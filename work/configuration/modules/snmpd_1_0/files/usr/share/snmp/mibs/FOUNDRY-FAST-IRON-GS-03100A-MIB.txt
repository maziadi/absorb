FOUNDRY-SN-ROOT-MIB DEFINITIONS ::= BEGIN

-- LAN Switch-Router Root MIB Release 1.0.1
-- Revision 01/30/99

-- Copyright 1996 Foundry Networks, Inc.
-- All rights reserved.
-- This Foundry SNMP Management Information Base Specification
-- (Specification) embodies Foundry's confidential and
-- proprietary intellectual property. Foundry retains all
-- title and ownership in the Specification, including any
-- revisions.

-- This Specification is supplied "AS IS," and Foundry makes
-- no warranty, either express or implied, as to the use,
-- operation, condition, or performance of the Specification.

-- SECTION 1: Top Level Definitions

 

IMPORTS
  enterprises
	FROM	RFC1155-SMI;	

foundry          OBJECT IDENTIFIER ::= { enterprises 1991 }
snTraps           OBJECT IDENTIFIER ::= { foundry 0 }
products        OBJECT IDENTIFIER ::= { foundry 1 }
vendors         OBJECT IDENTIFIER ::= { foundry 2 }

switch		OBJECT IDENTIFIER ::= { products 1 }
  snChassis		OBJECT IDENTIFIER ::= { switch 1 }
  snAgentSys	OBJECT IDENTIFIER ::= { switch 2 }
  snSwitch		OBJECT IDENTIFIER ::= { switch 3 }
  snL4			OBJECT IDENTIFIER ::= { switch 4 }
  snStack		OBJECT IDENTIFIER ::= { switch 5 }
  snSci			OBJECT IDENTIFIER ::= { switch 6 }

router 		OBJECT IDENTIFIER ::= { products 2 }
  snIpx			OBJECT IDENTIFIER ::= { router 1 }
  snIp			OBJECT IDENTIFIER ::= { router 2 }
  snRip			OBJECT IDENTIFIER ::= { router 3 }
  snOspf		OBJECT IDENTIFIER ::= { router 4 }
  snDvmrp		OBJECT IDENTIFIER ::= { router 5 }
  snIgmp		OBJECT IDENTIFIER ::= { router 6 }
  snFsrp		OBJECT IDENTIFIER ::= { router 7 }
  snGblRt		OBJECT IDENTIFIER ::= { router 8 }
  snPim			OBJECT IDENTIFIER ::= { router 9 }
  snAppleTalk	OBJECT IDENTIFIER ::= { router 10 }
  snBgp4		OBJECT IDENTIFIER ::= { router 11 }
  snVrrp		OBJECT IDENTIFIER ::= { router 12 }
  snLoopbackIf 	OBJECT IDENTIFIER ::= { router 13 }
  snPOS 		OBJECT IDENTIFIER ::= { router 14 }
  snMpls		OBJECT IDENTIFIER ::= { router 15 }

registration	OBJECT IDENTIFIER ::= { products 3 } -- sysObjectID values

  snFastIron        OBJECT IDENTIFIER ::= { registration 1 }   -- Stackable FastIron family
  snFIWGSwitch      OBJECT IDENTIFIER ::= { snFastIron 1 }     -- Stackable FastIron workgroup switch
  snFIBBSwitch      OBJECT IDENTIFIER ::= { snFastIron 2 }     -- Stackable FastIron backbone switch

  snNetIron         OBJECT IDENTIFIER ::= { registration 2 }   -- Stackable NetIron family
  snNIRouter        OBJECT IDENTIFIER ::= { snNetIron 1 }      -- Stackable NetIron router

  snServerIron      OBJECT IDENTIFIER ::= { registration 3 }   -- Stackable ServerIron family
  snSI              OBJECT IDENTIFIER ::= { snServerIron 1 }   -- Stackable ServerIron
  snSIXL            OBJECT IDENTIFIER ::= { snServerIron 2 }   -- Stackable ServerIronXL
  snSIXLTCS         OBJECT IDENTIFIER ::= { snServerIron 3 }   -- Stackable ServerIronXL TCS

  snTurboIron       OBJECT IDENTIFIER ::= { registration 4 }   -- Stackable TurboIron family
  snTISwitch        OBJECT IDENTIFIER ::= { snTurboIron 1 }    -- Stackable TurboIron switch
  snTIRouter        OBJECT IDENTIFIER ::= { snTurboIron 2 }    -- Stackable TurboIron router

  snTurboIron8      OBJECT IDENTIFIER ::= { registration 5 }   -- Stackable TurboIron 8 family
  snT8Switch        OBJECT IDENTIFIER ::= { snTurboIron8 1 }   -- Stackable TurboIron 8 switch
  snT8Router        OBJECT IDENTIFIER ::= { snTurboIron8 2 }   -- Stackable TurboIron 8 router
  snT8SI            OBJECT IDENTIFIER ::= { snTurboIron8 3 }
  snT8SIXLG         OBJECT IDENTIFIER ::= { snTurboIron8 4 }   -- Stackable ServerIronXLG

  snBigIron4000     OBJECT IDENTIFIER ::= { registration 6 }   -- BigIron 4000 family
  snBI4000Switch    OBJECT IDENTIFIER ::= { snBigIron4000 1 }  -- BigIron 4000 switch
  snBI4000Router    OBJECT IDENTIFIER ::= { snBigIron4000 2 }  -- BigIron 4000 router
  snBI4000SI        OBJECT IDENTIFIER ::= { snBigIron4000 3 }  -- BigServerIron

  snBigIron8000     OBJECT IDENTIFIER ::= { registration 7 }   -- BigIron 8000 family
  snBI8000Switch    OBJECT IDENTIFIER ::= { snBigIron8000 1 }  -- BigIron 8000 switch
  snBI8000Router    OBJECT IDENTIFIER ::= { snBigIron8000 2 }  -- BigIron 8000 router
  snBI8000SI        OBJECT IDENTIFIER ::= { snBigIron8000 3 }  -- BigServerIron

  snFastIron2       OBJECT IDENTIFIER ::= { registration 8 }   -- FastIron II family
  snFI2Switch       OBJECT IDENTIFIER ::= { snFastIron2 1 }    -- FastIron II switch
  snFI2Router       OBJECT IDENTIFIER ::= { snFastIron2 2 }    -- FastIron II router

  snFastIron2Plus   OBJECT IDENTIFIER ::= { registration 9 }     -- FastIron II Plus family
  snFI2PlusSwitch   OBJECT IDENTIFIER ::= { snFastIron2Plus 1 }  -- FastIron II Plus switch
  snFI2PlusRouter   OBJECT IDENTIFIER ::= { snFastIron2Plus 2 }  -- FastIron II Plus router

  snNetIron400      OBJECT IDENTIFIER ::= { registration 10 }  -- NetIron 400 family
  snNI400Router     OBJECT IDENTIFIER ::= { snNetIron400 1 }   -- NetIron 400 router

  snNetIron800      OBJECT IDENTIFIER ::= { registration 11 }  -- NetIron 800 family
  snNI800Router     OBJECT IDENTIFIER ::= { snNetIron800 1 }   -- NetIron 800 router

  snFastIron2GC     OBJECT IDENTIFIER ::= { registration 12 }  -- FastIron II GC family
  snFI2GCSwitch     OBJECT IDENTIFIER ::= { snFastIron2GC 1 }  -- FastIron II GC switch
  snFI2GCRouter     OBJECT IDENTIFIER ::= { snFastIron2GC 2 }  -- FastIron II GC router

  snFastIron2PlusGC OBJECT IDENTIFIER ::= { registration 13 }     -- FastIron II Plus GC family
  snFI2PlusGCSwitch OBJECT IDENTIFIER ::= { snFastIron2PlusGC 1 } -- FastIron II Plus GC switch
  snFI2PlusGCRouter OBJECT IDENTIFIER ::= { snFastIron2PlusGC 2 } -- FastIron II Plus GC router

  snBigIron15000    OBJECT IDENTIFIER ::= { registration 14 }   -- BigIron 15000 family
  snBI15000Switch   OBJECT IDENTIFIER ::= { snBigIron15000 1 }  -- BigIron 15000 switch
  snBI15000Router   OBJECT IDENTIFIER ::= { snBigIron15000 2 }  -- BigIron 15000 router
  snBI15000SI       OBJECT IDENTIFIER ::= { snBigIron15000 3 }

  snNetIron1500     OBJECT IDENTIFIER ::= { registration 15 }   -- NetIron 1500 family
  snNI1500Router    OBJECT IDENTIFIER ::= { snNetIron1500 1 }   -- NetIron 1500 router

  snFastIron3       OBJECT IDENTIFIER ::= { registration 16 }   -- FastIron III family
  snFI3Switch       OBJECT IDENTIFIER ::= { snFastIron3 1 }     -- FastIron III switch
  snFI3Router       OBJECT IDENTIFIER ::= { snFastIron3 2 }     -- FastIron III router

  snFastIron3GC     OBJECT IDENTIFIER ::= { registration 17 }   -- FastIron III GC family
  snFI3GCSwitch     OBJECT IDENTIFIER ::= { snFastIron3GC 1 }   -- FastIron III GC switch
  snFI3GCRouter     OBJECT IDENTIFIER ::= { snFastIron3GC 2 }   -- FastIron III GC router

  snServerIron400   OBJECT IDENTIFIER ::= { registration 18 }   -- ServerIron 400 family
  snSI400Switch     OBJECT IDENTIFIER ::= { snServerIron400 1 } -- ServerIron 400 switch
  snSI400Router     OBJECT IDENTIFIER ::= { snServerIron400 2 } -- ServerIron 400 router

  snServerIron800   OBJECT IDENTIFIER ::= { registration 19 }   -- ServerIron 800 family
  snSI800Switch     OBJECT IDENTIFIER ::= { snServerIron800 1 } -- ServerIron800 switch
  snSI800Router     OBJECT IDENTIFIER ::= { snServerIron800 2 } -- ServerIron800 router

  snServerIron1500  OBJECT IDENTIFIER ::= { registration 20 }    -- ServerIron 1500 family
  snSI1500Switch    OBJECT IDENTIFIER ::= { snServerIron1500 1 } -- ServerIron1500 switch
  snSI1500Router    OBJECT IDENTIFIER ::= { snServerIron1500 2 } -- ServerIron1500 router

  sn4802            OBJECT IDENTIFIER ::= { registration 21 }  -- Stackable 4802 family
  sn4802Switch      OBJECT IDENTIFIER ::= { sn4802 1 }         -- Stackable 4802 switch
  sn4802Router      OBJECT IDENTIFIER ::= { sn4802 2 }         -- Stackable 4802 router
  sn4802SI          OBJECT IDENTIFIER ::= { sn4802 3 }         -- Stackable 4802 ServerIron

  snFastIron400     OBJECT IDENTIFIER ::= { registration 22 } -- FastIron 400 family
  snFI400Switch     OBJECT IDENTIFIER ::= { snFastIron400 1 } -- FastIron 400 switch
  snFI400Router     OBJECT IDENTIFIER ::= { snFastIron400 2 } -- FastIron 400 router

  snFastIron800     OBJECT IDENTIFIER ::= { registration 23 } -- FastIron 800 family
  snFI800Switch     OBJECT IDENTIFIER ::= { snFastIron800 1 } -- FastIron800 switch
  snFI800Router     OBJECT IDENTIFIER ::= { snFastIron800 2 } -- FastIron800 router

  snFastIron1500    OBJECT IDENTIFIER ::= { registration 24 }  -- FastIron 1500 family
  snFI1500Switch    OBJECT IDENTIFIER ::= { snFastIron1500 1 } -- FastIron1500 switch
  snFI1500Router    OBJECT IDENTIFIER ::= { snFastIron1500 2 } -- FastIron1500 router

  snFES2402         OBJECT IDENTIFIER ::= { registration 25 } -- FastIron Edge Switch(FES) 2402
  snFES2402Switch   OBJECT IDENTIFIER ::= { snFES2402 1 }     -- FES2402 switch
  snFES2402Router   OBJECT IDENTIFIER ::= { snFES2402 2 }     -- FES2402 router

  snFES4802         OBJECT IDENTIFIER ::= { registration 26 } -- FastIron Edge Switch(FES) 4802
  snFES4802Switch   OBJECT IDENTIFIER ::= { snFES4802 1 }     -- FES4802 switch
  snFES4802Router   OBJECT IDENTIFIER ::= { snFES4802 2 }     -- FES4802 router

  snFES9604         OBJECT IDENTIFIER ::= { registration 27 } -- FastIron Edge Switch(FES) 9604
  snFES9604Switch   OBJECT IDENTIFIER ::= { snFES9604 1 }     -- FES9604 switch
  snFES9604Router   OBJECT IDENTIFIER ::= { snFES9604 2 }     -- FES9604 router

  snFES12GCF        OBJECT IDENTIFIER ::= { registration 28 }  -- FastIron Edge Switch(FES) 12GCF 
  snFES12GCFSwitch  OBJECT IDENTIFIER ::= { snFES12GCF 1 }  -- snFES12GCF switch 
  snFES12GCFRouter  OBJECT IDENTIFIER ::= { snFES12GCF 2 }  -- snFES12GCF router

  snFES2402POE        OBJECT IDENTIFIER ::= { registration 29 }   -- FastIron Edge Switch(FES) 2402 POE 
  snFES2402POESwitch  OBJECT IDENTIFIER ::= { snFES2402POE 1 }  -- snFES2402POE switch 
  snFES2402POERouter  OBJECT IDENTIFIER ::= { snFES2402POE 2 }  -- snFES2402POE router

  snFES4802POE        OBJECT IDENTIFIER ::= { registration 30 }   -- FastIron Edge Switch (FES) 4802 POE 
  snFES4802POESwitch  OBJECT IDENTIFIER ::= { snFES4802POE 1 } -- snFES4802POE switch 
  snFES4802POERouter  OBJECT IDENTIFIER ::= { snFES4802POE 2 } -- snFES4802POE router

  snNetIron4802     OBJECT IDENTIFIER ::= { registration 31 }     -- NetIron 4802 family 
  snNI4802Switch    OBJECT IDENTIFIER ::= { snNetIron4802 1 }   -- NetIron 4802 switch
  snNI4802Router    OBJECT IDENTIFIER ::= { snNetIron4802 2 }   -- NetIron 4802 router

  snBigIronMG8      OBJECT IDENTIFIER ::= { registration 32 }   -- BigIron MG8 family
  snBIMG8Switch     OBJECT IDENTIFIER ::= { snBigIronMG8 1 }    -- BigIron MG8 switch
  snBIMG8Router     OBJECT IDENTIFIER ::= { snBigIronMG8 2 }    -- BigIron MG8 router

  snNetIron40G      OBJECT IDENTIFIER ::= { registration 33 }   -- NetIron 40G family
  snNI40GRouter     OBJECT IDENTIFIER ::= { snNetIron40G 2 }    -- NetIron 40G router

  snFESXFamily      OBJECT IDENTIFIER ::= { registration 34 }

  snFESX424Family   OBJECT IDENTIFIER ::= { snFESXFamily 1 }

  snFESX424BaseFamily   OBJECT IDENTIFIER ::= { snFESX424Family 1 }
  snFESX424             OBJECT IDENTIFIER ::= { snFESX424BaseFamily 1 }  -- FastIron Edge Switch(FES) 24G
  snFESX424Switch       OBJECT IDENTIFIER ::= { snFESX424 1 }            -- FESX424 switch
  snFESX424Router       OBJECT IDENTIFIER ::= { snFESX424 2 }            -- FESX424 router
  snFESX424Prem         OBJECT IDENTIFIER ::= { snFESX424BaseFamily 2 }  -- FastIron Edge Switch(FES) 24G-PREM
  snFESX424PremSwitch   OBJECT IDENTIFIER ::= { snFESX424Prem 1 }        -- FESX424-PREM switch
  snFESX424PremRouter   OBJECT IDENTIFIER ::= { snFESX424Prem 2 }        -- FESX424-PREM router

  snFESX424Plus1XGFamily     OBJECT IDENTIFIER ::= { snFESX424Family 2 }
  snFESX424Plus1XG           OBJECT IDENTIFIER ::= { snFESX424Plus1XGFamily 1 } -- FastIron Edge Switch(FES) 24G + 1 10G
  snFESX424Plus1XGSwitch     OBJECT IDENTIFIER ::= { snFESX424Plus1XG 1 }     -- FESX424+1XG switch
  snFESX424Plus1XGRouter     OBJECT IDENTIFIER ::= { snFESX424Plus1XG 2 }     -- FESX424+1XG router
  snFESX424Plus1XGPrem       OBJECT IDENTIFIER ::= { snFESX424Plus1XGFamily 2 } -- FastIron Edge Switch(FES) 24G + 1 10G-PREM
  snFESX424Plus1XGPremSwitch OBJECT IDENTIFIER ::= { snFESX424Plus1XGPrem 1 } -- FESX424+1XG-PREM switch
  snFESX424Plus1XGPremRouter OBJECT IDENTIFIER ::= { snFESX424Plus1XGPrem 2 } -- FESX424+1XG-PREM router

  snFESX424Plus2XGFamily     OBJECT IDENTIFIER ::= { snFESX424Family 3 }
  snFESX424Plus2XG           OBJECT IDENTIFIER ::= { snFESX424Plus2XGFamily 1 } -- FastIron Edge Switch(FES) 24G + 2 10G
  snFESX424Plus2XGSwitch     OBJECT IDENTIFIER ::= { snFESX424Plus2XG 1 }     -- FESX424+2XG switch
  snFESX424Plus2XGRouter     OBJECT IDENTIFIER ::= { snFESX424Plus2XG 2 }     -- FESX424+2XG router
  snFESX424Plus2XGPrem       OBJECT IDENTIFIER ::= { snFESX424Plus2XGFamily 2 } -- FastIron Edge Switch(FES) 24G + 2 10G-PREM
  snFESX424Plus2XGPremSwitch OBJECT IDENTIFIER ::= { snFESX424Plus2XGPrem 1 } -- FESX424+2XG-PREM switch
  snFESX424Plus2XGPremRouter OBJECT IDENTIFIER ::= { snFESX424Plus2XGPrem 2 } -- FESX424+2XG-PREM router

  snFESX448Family         OBJECT IDENTIFIER ::= { snFESXFamily 2 }

  snFESX448BaseFamily     OBJECT IDENTIFIER ::= { snFESX448Family 1 }
  snFESX448               OBJECT IDENTIFIER ::= { snFESX448BaseFamily 1 }    -- FastIron Edge Switch(FES) 48G
  snFESX448Switch         OBJECT IDENTIFIER ::= { snFESX448 1 }            -- FESX448 switch
  snFESX448Router         OBJECT IDENTIFIER ::= { snFESX448 2 }            -- FESX448 router
  snFESX448Prem           OBJECT IDENTIFIER ::= { snFESX448BaseFamily 2 }    -- FastIron Edge Switch(FES) 48G-PREM
  snFESX448PremSwitch     OBJECT IDENTIFIER ::= { snFESX448Prem 1 }        -- FESX448-PREM switch
  snFESX448PremRouter     OBJECT IDENTIFIER ::= { snFESX448Prem 2 }        -- FESX448-PREM router

  snFESX448Plus1XGFamily     OBJECT IDENTIFIER ::= { snFESX448Family 2 }
  snFESX448Plus1XG           OBJECT IDENTIFIER ::= { snFESX448Plus1XGFamily 1 } -- FastIron Edge Switch(FES) 48G + 1 10G
  snFESX448Plus1XGSwitch     OBJECT IDENTIFIER ::= { snFESX448Plus1XG 1 }     -- FESX448+1XG switch
  snFESX448Plus1XGRouter     OBJECT IDENTIFIER ::= { snFESX448Plus1XG 2 }     -- FESX448+1XG router
  snFESX448Plus1XGPrem       OBJECT IDENTIFIER ::= { snFESX448Plus1XGFamily 2 } -- FastIron Edge Switch(FES) 48G + 1 10G-PREM
  snFESX448Plus1XGPremSwitch OBJECT IDENTIFIER ::= { snFESX448Plus1XGPrem 1 } -- FESX448+1XG-PREM switch
  snFESX448Plus1XGPremRouter OBJECT IDENTIFIER ::= { snFESX448Plus1XGPrem 2 } -- FESX448+1XG-PREM router

  snFESX448Plus2XGFamily     OBJECT IDENTIFIER ::= { snFESX448Family 3 }
  snFESX448Plus2XG           OBJECT IDENTIFIER ::= { snFESX448Plus2XGFamily 1 } -- FastIron Edge Switch(FES) 48G + 2 10G
  snFESX448Plus2XGSwitch     OBJECT IDENTIFIER ::= { snFESX448Plus2XG 1 }     -- FESX448+2XG switch
  snFESX448Plus2XGRouter     OBJECT IDENTIFIER ::= { snFESX448Plus2XG 2 }     -- FESX448+2XG router
  snFESX448Plus2XGPrem       OBJECT IDENTIFIER ::= { snFESX448Plus2XGFamily 2 } -- FastIron Edge Switch(FES) 48G + 2 10G-PREM
  snFESX448Plus2XGPremSwitch OBJECT IDENTIFIER ::= { snFESX448Plus2XGPrem 1 } -- FESX448+2XG-PREM switch
  snFESX448Plus2XGPremRouter OBJECT IDENTIFIER ::= { snFESX448Plus2XGPrem 2 } -- FESX448+2XG-PREM router

  snFESX424FiberFamily       OBJECT IDENTIFIER ::= { snFESXFamily 3 }

  snFESX424FiberBaseFamily     OBJECT IDENTIFIER ::= { snFESX424FiberFamily 1 }
  snFESX424Fiber                 OBJECT IDENTIFIER ::= { snFESX424FiberBaseFamily 1 }    -- FastIron Edge Switch(FES)Fiber 24G
  snFESX424FiberSwitch             OBJECT IDENTIFIER ::= { snFESX424Fiber 1 }            -- FESX424Fiber switch
  snFESX424FiberRouter             OBJECT IDENTIFIER ::= { snFESX424Fiber 2 }            -- FESX424Fiber router
  snFESX424FiberPrem             OBJECT IDENTIFIER ::= { snFESX424FiberBaseFamily 2 }    -- FastIron Edge Switch(FES)Fiber 24G-PREM
  snFESX424FiberPremSwitch         OBJECT IDENTIFIER ::= { snFESX424FiberPrem 1 }        -- FESX424Fiber-PREM switch
  snFESX424FiberPremRouter         OBJECT IDENTIFIER ::= { snFESX424FiberPrem 2 }        -- FESX424Fiber-PREM router

  snFESX424FiberPlus1XGFamily  OBJECT IDENTIFIER ::= { snFESX424FiberFamily 2 }
  snFESX424FiberPlus1XG          OBJECT IDENTIFIER ::= { snFESX424FiberPlus1XGFamily 1 } -- FastIron Edge Switch(FES)Fiber 24G + 1 10G
  snFESX424FiberPlus1XGSwitch      OBJECT IDENTIFIER ::= { snFESX424FiberPlus1XG 1 }     -- FESX424Fiber+1XG switch
  snFESX424FiberPlus1XGRouter      OBJECT IDENTIFIER ::= { snFESX424FiberPlus1XG 2 }     -- FESX424Fiber+1XG router
  snFESX424FiberPlus1XGPrem      OBJECT IDENTIFIER ::= { snFESX424FiberPlus1XGFamily 2 } -- FastIron Edge Switch(FES)Fiber 24G + 1 10G-PREM
  snFESX424FiberPlus1XGPremSwitch  OBJECT IDENTIFIER ::= { snFESX424FiberPlus1XGPrem 1 } -- FESX424Fiber+1XG-PREM switch
  snFESX424FiberPlus1XGPremRouter  OBJECT IDENTIFIER ::= { snFESX424FiberPlus1XGPrem 2 } -- FESX424Fiber+1XG-PREM router

  snFESX424FiberPlus2XGFamily  OBJECT IDENTIFIER ::= { snFESX424FiberFamily 3 }
  snFESX424FiberPlus2XG          OBJECT IDENTIFIER ::= { snFESX424FiberPlus2XGFamily 1 } -- FastIron Edge Switch(FES)Fiber 24G + 2 10G
  snFESX424FiberPlus2XGSwitch      OBJECT IDENTIFIER ::= { snFESX424FiberPlus2XG 1 }     -- FESX424Fiber+2XG switch
  snFESX424FiberPlus2XGRouter      OBJECT IDENTIFIER ::= { snFESX424FiberPlus2XG 2 }     -- FESX424Fiber+2XG router
  snFESX424FiberPlus2XGPrem      OBJECT IDENTIFIER ::= { snFESX424FiberPlus2XGFamily 2 } -- FastIron Edge Switch(FES)Fiber 24G + 2 10G-PREM
  snFESX424FiberPlus2XGPremSwitch  OBJECT IDENTIFIER ::= { snFESX424FiberPlus2XGPrem 1 } -- FESX424Fiber+2XG-PREM switch
  snFESX424FiberPlus2XGPremRouter  OBJECT IDENTIFIER ::= { snFESX424FiberPlus2XGPrem 2 } -- FESX424Fiber+2XG-PREM router

  snFESX448FiberFamily       OBJECT IDENTIFIER ::= { snFESXFamily 4 }

  snFESX448FiberBaseFamily     OBJECT IDENTIFIER ::= { snFESX448FiberFamily 1 }
  snFESX448Fiber                 OBJECT IDENTIFIER ::= { snFESX448FiberBaseFamily 1 }    -- FastIron Edge Switch(FES)Fiber 48G
  snFESX448FiberSwitch             OBJECT IDENTIFIER ::= { snFESX448Fiber 1 }            -- FESX448Fiber switch
  snFESX448FiberRouter             OBJECT IDENTIFIER ::= { snFESX448Fiber 2 }            -- FESX448Fiber router
  snFESX448FiberPrem             OBJECT IDENTIFIER ::= { snFESX448FiberBaseFamily 2 }    -- FastIron Edge Switch(FES)Fiber 48G-PREM
  snFESX448FiberPremSwitch         OBJECT IDENTIFIER ::= { snFESX448FiberPrem 1 }        -- FESX448Fiber-PREM switch
  snFESX448FiberPremRouter         OBJECT IDENTIFIER ::= { snFESX448FiberPrem 2 }        -- FESX448Fiber-PREM router

  snFESX448FiberPlus1XGFamily  OBJECT IDENTIFIER ::= { snFESX448FiberFamily 2 }
  snFESX448FiberPlus1XG          OBJECT IDENTIFIER ::= { snFESX448FiberPlus1XGFamily 1 } -- FastIron Edge Switch(FES)Fiber 48G + 1 10G
  snFESX448FiberPlus1XGSwitch      OBJECT IDENTIFIER ::= { snFESX448FiberPlus1XG 1 }     -- FESX448Fiber+1XG switch
  snFESX448FiberPlus1XGRouter      OBJECT IDENTIFIER ::= { snFESX448FiberPlus1XG 2 }     -- FESX448Fiber+1XG router
  snFESX448FiberPlus1XGPrem      OBJECT IDENTIFIER ::= { snFESX448FiberPlus1XGFamily 2 } -- FastIron Edge Switch(FES)Fiber 48G + 1 10G-PREM
  snFESX448FiberPlus1XGPremSwitch  OBJECT IDENTIFIER ::= { snFESX448FiberPlus1XGPrem 1 } -- FESX448Fiber+1XG-PREM switch
  snFESX448FiberPlus1XGPremRouter  OBJECT IDENTIFIER ::= { snFESX448FiberPlus1XGPrem 2 } -- FESX448Fiber+1XG-PREM router

  snFESX448FiberPlus2XGFamily  OBJECT IDENTIFIER ::= { snFESX448FiberFamily 3 }
  snFESX448FiberPlus2XG          OBJECT IDENTIFIER ::= { snFESX448FiberPlus2XGFamily 1 } -- FastIron Edge Switch(FES)Fiber 48G + 2 10G
  snFESX448FiberPlus2XGSwitch      OBJECT IDENTIFIER ::= { snFESX448FiberPlus2XG 1 }     -- FESX448Fiber+2XG switch
  snFESX448FiberPlus2XGRouter      OBJECT IDENTIFIER ::= { snFESX448FiberPlus2XG 2 }     -- FESX448+2XG router
  snFESX448FiberPlus2XGPrem      OBJECT IDENTIFIER ::= { snFESX448FiberPlus2XGFamily 2 } -- FastIron Edge Switch(FES)Fiber 48G + 2 10G-PREM
  snFESX448FiberPlus2XGPremSwitch  OBJECT IDENTIFIER ::= { snFESX448FiberPlus2XGPrem 1 } -- FESX448Fiber+2XG-PREM switch
  snFESX448FiberPlus2XGPremRouter  OBJECT IDENTIFIER ::= { snFESX448FiberPlus2XGPrem 2 } -- FESX448Fiber+2XG-PREM router

  snFESX424POEFamily       OBJECT IDENTIFIER ::= { snFESXFamily 5 }

  snFESX424POEBaseFamily    OBJECT IDENTIFIER ::= { snFESX424POEFamily 1 }
  snFESX424POE                 OBJECT IDENTIFIER ::= { snFESX424POEBaseFamily 1 }    -- FastIron Edge Switch(FES) 24G POE
  snFESX424POESwitch             OBJECT IDENTIFIER ::= { snFESX424POE 1 }            -- FESX424POE switch
  snFESX424POERouter             OBJECT IDENTIFIER ::= { snFESX424POE 2 }            -- FESX424POE router
  snFESX424POEPrem             OBJECT IDENTIFIER ::= { snFESX424POEBaseFamily 2 }    -- FastIron Edge Switch(FES) 24GPOE-PREM
  snFESX424POEPremSwitch         OBJECT IDENTIFIER ::= { snFESX424POEPrem 1 }        -- FESX424POE-PREM switch
  snFESX424POEPremRouter         OBJECT IDENTIFIER ::= { snFESX424POEPrem 2 }        -- FESX424POE-PREM router

  snFESX424POEPlus1XGFamily  OBJECT IDENTIFIER ::= { snFESX424POEFamily 2 }
  snFESX424POEPlus1XG          OBJECT IDENTIFIER ::= { snFESX424POEPlus1XGFamily 1 } -- FastIron Edge Switch(FES) 24GPOE + 1 10G
  snFESX424POEPlus1XGSwitch      OBJECT IDENTIFIER ::= { snFESX424POEPlus1XG 1 }     -- FESX424POE+1XG switch
  snFESX424POEPlus1XGRouter      OBJECT IDENTIFIER ::= { snFESX424POEPlus1XG 2 }     -- FESX424POE+1XG router
  snFESX424POEPlus1XGPrem      OBJECT IDENTIFIER ::= { snFESX424POEPlus1XGFamily 2 } -- FastIron Edge Switch(FES) 24GPOE + 1 10G-PREM
  snFESX424POEPlus1XGPremSwitch  OBJECT IDENTIFIER ::= { snFESX424POEPlus1XGPrem 1 } -- FESX424POE+1XG-PREM switch
  snFESX424POEPlus1XGPremRouter  OBJECT IDENTIFIER ::= { snFESX424POEPlus1XGPrem 2 } -- FESX424POE+1XG-PREM router

  snFESX424POEPlus2XGFamily  OBJECT IDENTIFIER ::= { snFESX424POEFamily 3 }
  snFESX424POEPlus2XG          OBJECT IDENTIFIER ::= { snFESX424POEPlus2XGFamily 1 } -- FastIron Edge Switch(FES) 24GPOE + 2 10G
  snFESX424POEPlus2XGSwitch      OBJECT IDENTIFIER ::= { snFESX424POEPlus2XG 1 }     -- FESX424POE+2XG switch
  snFESX424POEPlus2XGRouter      OBJECT IDENTIFIER ::= { snFESX424POEPlus2XG 2 }     -- FESX424POE+2XG router
  snFESX424POEPlus2XGPrem      OBJECT IDENTIFIER ::= { snFESX424POEPlus2XGFamily 2 } -- FastIron Edge Switch(FES) 24GPOE + 2 10G-PREM
  snFESX424POEPlus2XGPremSwitch  OBJECT IDENTIFIER ::= { snFESX424POEPlus2XGPrem 1 } -- FESX424POE+2XG-PREM switch
  snFESX424POEPlus2XGPremRouter  OBJECT IDENTIFIER ::= { snFESX424POEPlus2XGPrem 2 } -- FESX424POE+2XG-PREM router

  snFWSXFamily          OBJECT IDENTIFIER ::= { registration 35 }

  snFWSX424Family       OBJECT IDENTIFIER ::= { snFWSXFamily 1 }
  snFWSX424BaseFamily   OBJECT IDENTIFIER ::= { snFWSX424Family 1 }
  snFWSX424             OBJECT IDENTIFIER ::= { snFWSX424BaseFamily 1 }    -- FastIron WorkGroup Switch(FWS) 24G
  snFWSX424Switch       OBJECT IDENTIFIER ::= { snFWSX424 1 }            -- FWSX424 switch
  snFWSX424Router       OBJECT IDENTIFIER ::= { snFWSX424 2 }            -- FWSX424 router

  snFWSX424Plus1XGFamily   OBJECT IDENTIFIER ::= { snFWSX424Family 2 }
  snFWSX424Plus1XG         OBJECT IDENTIFIER ::= { snFWSX424Plus1XGFamily 1 } -- FastIron WorkGroup Switch(FWS) 24G + 1 10G
  snFWSX424Plus1XGSwitch   OBJECT IDENTIFIER ::= { snFWSX424Plus1XG 1 }     -- FWSX424+1XG switch
  snFWSX424Plus1XGRouter   OBJECT IDENTIFIER ::= { snFWSX424Plus1XG 2 }     -- FWSX424+1XG router

  snFWSX424Plus2XGFamily  OBJECT IDENTIFIER ::= { snFWSX424Family 3 }
  snFWSX424Plus2XG        OBJECT IDENTIFIER ::= { snFWSX424Plus2XGFamily 1 } -- FastIron WorkGroup Switch(FWS) 24G + 2 10G
  snFWSX424Plus2XGSwitch  OBJECT IDENTIFIER ::= { snFWSX424Plus2XG 1 }     -- FWSX424+2XG switch
  snFWSX424Plus2XGRouter  OBJECT IDENTIFIER ::= { snFWSX424Plus2XG 2 }     -- FWSX424+2XG router

  snFWSX448Family         OBJECT IDENTIFIER ::= { snFWSXFamily 2 }
  snFWSX448BaseFamily     OBJECT IDENTIFIER ::= { snFWSX448Family 1 }
  snFWSX448               OBJECT IDENTIFIER ::= { snFWSX448BaseFamily 1 }    -- FastIron WorkGroup Switch(FWS) 48G
  snFWSX448Switch         OBJECT IDENTIFIER ::= { snFWSX448 1 }            -- FWSX448 switch
  snFWSX448Router         OBJECT IDENTIFIER ::= { snFWSX448 2 }            -- FWSX448 router

  snFWSX448Plus1XGFamily  OBJECT IDENTIFIER ::= { snFWSX448Family 2 }
  snFWSX448Plus1XG        OBJECT IDENTIFIER ::= { snFWSX448Plus1XGFamily 1 } -- FastIron WorkGroup Switch(FWS) 48G + 1 10G
  snFWSX448Plus1XGSwitch  OBJECT IDENTIFIER ::= { snFWSX448Plus1XG 1 }     -- FWSX448+1XG switch
  snFWSX448Plus1XGRouter  OBJECT IDENTIFIER ::= { snFWSX448Plus1XG 2 }     -- FWSX448+1XG router

  snFWSX448Plus2XGFamily  OBJECT IDENTIFIER ::= { snFWSX448Family 3 }
  snFWSX448Plus2XG        OBJECT IDENTIFIER ::= { snFWSX448Plus2XGFamily 1 } -- FastIron WorkGroup Switch(FWS) 48G + 2 10G
  snFWSX448Plus2XGSwitch  OBJECT IDENTIFIER ::= { snFWSX448Plus2XG 1 }     -- FWSX448+2XG switch
  snFWSX448Plus2XGRouter  OBJECT IDENTIFIER ::= { snFWSX448Plus2XG 2 }     -- FWSX448+2XG router

-- Do not use { snFWSXFamily 3 } to { snFWSXFamily 4 }

  snFastIronSuperXFamily            OBJECT IDENTIFIER ::= { registration 36 }        -- FastIron SuperX Family
  snFastIronSuperX                  OBJECT IDENTIFIER ::= { snFastIronSuperXFamily 1 }    -- FastIron SuperX
  snFastIronSuperXSwitch            OBJECT IDENTIFIER ::= { snFastIronSuperX 1 }          -- FastIron SuperX Switch
  snFastIronSuperXRouter            OBJECT IDENTIFIER ::= { snFastIronSuperX 2 }          -- FastIron SuperX Router
  snFastIronSuperXBaseL3Switch      OBJECT IDENTIFIER ::= { snFastIronSuperX 3 }          -- FastIron SuperX Base L3 Switch
  snFastIronSuperXPrem              OBJECT IDENTIFIER ::= { snFastIronSuperXFamily 2 }    -- FastIron SuperX Premium
  snFastIronSuperXPremSwitch        OBJECT IDENTIFIER ::= { snFastIronSuperXPrem 1 }      -- FastIron SuperX Premium Switch
  snFastIronSuperXPremRouter        OBJECT IDENTIFIER ::= { snFastIronSuperXPrem 2 }      -- FastIron SuperX Premium Router
  snFastIronSuperXPremBaseL3Switch  OBJECT IDENTIFIER ::= { snFastIronSuperXPrem 3 }      -- FastIron SuperX Premium Base L3 Switch

  snFastIronSuperX800                  OBJECT IDENTIFIER ::= { snFastIronSuperXFamily 3 }    -- FastIron SuperX 800 
  snFastIronSuperX800Switch            OBJECT IDENTIFIER ::= { snFastIronSuperX800 1 }          -- FastIron SuperX 800 Switch
  snFastIronSuperX800Router            OBJECT IDENTIFIER ::= { snFastIronSuperX800 2 }          -- FastIron SuperX 800 Router
  snFastIronSuperX800BaseL3Switch      OBJECT IDENTIFIER ::= { snFastIronSuperX800 3 }          -- FastIron SuperX 800 Base L3 Switch
  snFastIronSuperX800Prem              OBJECT IDENTIFIER ::= { snFastIronSuperXFamily 4 }    -- FastIron SuperX 800 Premium
  snFastIronSuperX800PremSwitch        OBJECT IDENTIFIER ::= { snFastIronSuperX800Prem 1 }      -- FastIron SuperX 800 Premium Switch
  snFastIronSuperX800PremRouter        OBJECT IDENTIFIER ::= { snFastIronSuperX800Prem 2 }      -- FastIron SuperX 800 Premium Router
  snFastIronSuperX800PremBaseL3Switch  OBJECT IDENTIFIER ::= { snFastIronSuperX800Prem 3 }      -- FastIron SuperX 800 Premium Base L3 Switch

  snFastIronSuperX1600                  OBJECT IDENTIFIER ::= { snFastIronSuperXFamily 5 }    -- FastIron SuperX 1600 
  snFastIronSuperX1600Switch            OBJECT IDENTIFIER ::= { snFastIronSuperX1600 1 }          -- FastIron SuperX 1600 Switch
  snFastIronSuperX1600Router            OBJECT IDENTIFIER ::= { snFastIronSuperX1600 2 }          -- FastIron SuperX 1600 Router
  snFastIronSuperX1600BaseL3Switch      OBJECT IDENTIFIER ::= { snFastIronSuperX1600 3 }          -- FastIron SuperX 1600 Base L3 Switch
  snFastIronSuperX1600Prem              OBJECT IDENTIFIER ::= { snFastIronSuperXFamily 6 }    -- FastIron SuperX 1600 Premium
  snFastIronSuperX1600PremSwitch        OBJECT IDENTIFIER ::= { snFastIronSuperX1600Prem 1 }      -- FastIron SuperX 1600 Premium Switch
  snFastIronSuperX1600PremRouter        OBJECT IDENTIFIER ::= { snFastIronSuperX1600Prem 2 }      -- FastIron SuperX 1600 Premium Router
  snFastIronSuperX1600PremBaseL3Switch  OBJECT IDENTIFIER ::= { snFastIronSuperX1600Prem 3 }      -- FastIron SuperX 1600 Premium Base L3 Switch

  snBigIronSuperXFamily             OBJECT IDENTIFIER ::= { registration 37 }        -- BigIron SuperX Family
  snBigIronSuperX                   OBJECT IDENTIFIER ::= { snBigIronSuperXFamily 1 }    -- BigIron SuperX
  snBigIronSuperXSwitch             OBJECT IDENTIFIER ::= { snBigIronSuperX 1 }          -- BigIron SuperX Switch
  snBigIronSuperXRouter             OBJECT IDENTIFIER ::= { snBigIronSuperX 2 }          -- BigIron SuperX Router
  snBigIronSuperXBaseL3Switch       OBJECT IDENTIFIER ::= { snBigIronSuperX 3 }          -- BigIron SuperX Base L3 Switch

  snTurboIronSuperXFamily           OBJECT IDENTIFIER ::= { registration 38 }        -- TurboIron SuperX Family
  snTurboIronSuperX                 OBJECT IDENTIFIER ::= { snTurboIronSuperXFamily 1 }    -- TurboIron SuperX
  snTurboIronSuperXSwitch           OBJECT IDENTIFIER ::= { snTurboIronSuperX 1 }          -- TurboIron SuperX Switch
  snTurboIronSuperXRouter           OBJECT IDENTIFIER ::= { snTurboIronSuperX 2 }          -- TurboIron SuperX Router
  snTurboIronSuperXBaseL3Switch     OBJECT IDENTIFIER ::= { snTurboIronSuperX 3 }          -- TurboIron SuperX Base L3 Switch
  snTurboIronSuperXPrem             OBJECT IDENTIFIER ::= { snTurboIronSuperXFamily 2 }    -- TurboIron SuperX Premium
  snTurboIronSuperXPremSwitch       OBJECT IDENTIFIER ::= { snTurboIronSuperXPrem 1 }      -- TurboIron SuperX Premium Switch
  snTurboIronSuperXPremRouter       OBJECT IDENTIFIER ::= { snTurboIronSuperXPrem 2 }      -- TurboIron SuperX Premium Router
  snTurboIronSuperXPremBaseL3Switch OBJECT IDENTIFIER ::= { snTurboIronSuperXPrem 3 }      -- TurboIron SuperX Premium Base L3 Switch


  snIMRFamily       OBJECT IDENTIFIER ::= { registration 39 }
  snNetIronIMR      OBJECT IDENTIFIER ::= { snIMRFamily 1 }     -- NetIron IMR family
  snNIIMRRouter     OBJECT IDENTIFIER ::= { snNetIronIMR 2 }    -- NetIron IMR router

  snBigIronRXFamily OBJECT IDENTIFIER ::= { registration 40 }      -- BigIron RX family
  snBigIronRX16     OBJECT IDENTIFIER ::= { snBigIronRXFamily 1 }  -- BigIron RX16 family
  snBIRX16Switch    OBJECT IDENTIFIER ::= { snBigIronRX16 1 }      -- BigIron RX16 switch
  snBIRX16Router    OBJECT IDENTIFIER ::= { snBigIronRX16 2 }      -- BigIron RX16 router
  snBigIronRX8      OBJECT IDENTIFIER ::= { snBigIronRXFamily 2 }  -- BigIron RX8 family
  snBIRX8Switch     OBJECT IDENTIFIER ::= { snBigIronRX8 1 }       -- BigIron RX8 switch
  snBIRX8Router     OBJECT IDENTIFIER ::= { snBigIronRX8 2 }       -- BigIron RX8 router
  snBigIronRX4      OBJECT IDENTIFIER ::= { snBigIronRXFamily 3 }  -- BigIron RX4 family
  snBIRX4Switch     OBJECT IDENTIFIER ::= { snBigIronRX4 1 }       -- BigIron RX4 switch
  snBIRX4Router     OBJECT IDENTIFIER ::= { snBigIronRX4 2 }       -- BigIron RX4 router

  snNetIronXMRFamily OBJECT IDENTIFIER ::= { registration 41 }      -- NetIron XMR family
  snNetIronXMR16000     OBJECT IDENTIFIER ::= { snNetIronXMRFamily 1 }  -- NetIron XMR16000 family
  snNIXMR16000Router    OBJECT IDENTIFIER ::= { snNetIronXMR16000 2 }      -- NetIron XMR16000 router
  snNetIronXMR8000      OBJECT IDENTIFIER ::= { snNetIronXMRFamily 2 }  -- NetIron XMR8000 family
  snNIXMR8000Router     OBJECT IDENTIFIER ::= { snNetIronXMR8000 2 }       -- NetIron XMR8000 router
  snNetIronXMR4000      OBJECT IDENTIFIER ::= { snNetIronXMRFamily 3 }  -- NetIron XMR4000 family
  snNIXMR4000Router     OBJECT IDENTIFIER ::= { snNetIronXMR4000 2 }       -- NetIron XMR4000 router

  snSecureIronFamily            OBJECT IDENTIFIER ::= {  registration 42 }    -- SecureIron family
-- Do not use { snSecureIronFamily 1 } to { snSecureIronFamily 8 }
  snSecureIronLSFamily          OBJECT IDENTIFIER ::= { snSecureIronFamily 9 }    -- SecureIron LS family
  snSecureIronLS100             OBJECT IDENTIFIER ::= { snSecureIronLSFamily 1 }  -- SecureIronLS 100
  snSecureIronLS100Switch       OBJECT IDENTIFIER ::= { snSecureIronLS100 1 }     -- SecureIronLS 100 Switch
  snSecureIronLS100Router       OBJECT IDENTIFIER ::= { snSecureIronLS100 2 }     -- SecureIronLS 100 Router
  snSecureIronLS300             OBJECT IDENTIFIER ::= { snSecureIronLSFamily 2 }  -- SecureIronLS 300
  snSecureIronLS300Switch       OBJECT IDENTIFIER ::= { snSecureIronLS300 1 }     -- SecureIronLS 300 Switch
  snSecureIronLS300Router       OBJECT IDENTIFIER ::= { snSecureIronLS300 2 }     -- SecureIronLS 300 Router
  snSecureIronTMFamily          OBJECT IDENTIFIER ::= { snSecureIronFamily 10 }   -- SecureIron TM family
  snSecureIronTM100             OBJECT IDENTIFIER ::= { snSecureIronTMFamily 1 }  -- SecureIronTM 100
  snSecureIronTM100Switch       OBJECT IDENTIFIER ::= { snSecureIronTM100 1 }     -- SecureIronTM 100 Switch
  snSecureIronTM100Router       OBJECT IDENTIFIER ::= { snSecureIronTM100 2 }     -- SecureIronTM 100 Router
  snSecureIronTM300             OBJECT IDENTIFIER ::= { snSecureIronTMFamily 2 }  -- SecureIronTM 300
  snSecureIronTM300Switch       OBJECT IDENTIFIER ::= { snSecureIronTM300 1 }     -- SecureIronTM 300 Switch
  snSecureIronTM300Router       OBJECT IDENTIFIER ::= { snSecureIronTM300 2 }     -- SecureIronTM 300 Router

-- Do not use { registration 43 }

  snNetIronMLXFamily OBJECT IDENTIFIER ::= { registration 44 }      -- NetIron MLX family
  snNetIronMLX16      OBJECT IDENTIFIER ::= { snNetIronMLXFamily 1 }  -- NetIron MLX-16 family
  snNetIronMLX16Router     OBJECT IDENTIFIER ::= { snNetIronMLX16 2 }       -- NetIron MLX-16 router
  snNetIronMLX8      OBJECT IDENTIFIER ::= { snNetIronMLXFamily 2 }  -- NetIron MLX-8 family
  snNetIronMLX8Router     OBJECT IDENTIFIER ::= { snNetIronMLX8 2 }       -- NetIron MLX-8 router
  snNetIronMLX4      OBJECT IDENTIFIER ::= { snNetIronMLXFamily 3 }  -- NetIron MLX-4 family
  snNetIronMLX4Router     OBJECT IDENTIFIER ::= { snNetIronMLX4 2 }       -- NetIron MLX-4 router


  snFGSFamily          OBJECT IDENTIFIER ::= { registration 45 }	-- FastIron GS series family
  snFGS624Family       OBJECT IDENTIFIER ::= { snFGSFamily 1 }

  snFGS624PBaseFamily  OBJECT IDENTIFIER ::= { snFGS624Family 1 }
  snFGS624P            OBJECT IDENTIFIER ::= { snFGS624PBaseFamily 1 }  -- FastIron GS Switch(FGS) 24-port 10/100/1000 POE Ready
  snFGS624PSwitch      OBJECT IDENTIFIER ::= { snFGS624P 1 }            -- FGS624P switch
  snFGS624PRouter      OBJECT IDENTIFIER ::= { snFGS624P 2 }            -- FGS624P router

  snFGS624XGPFamily    OBJECT IDENTIFIER ::= { snFGS624Family 2 }
  snFGS624XGP          OBJECT IDENTIFIER ::= { snFGS624XGPFamily 1 }    -- FastIron GS Switch(FGS) 24-port 10/100/1000 POE Ready + 1 10G
  snFGS624XGPSwitch    OBJECT IDENTIFIER ::= { snFGS624XGP 1 }          -- FGS624XGP switch
  snFGS624XGPRouter    OBJECT IDENTIFIER ::= { snFGS624XGP 2 }          -- FGS624XGP router

  snFGS624PPOEFamily   OBJECT IDENTIFIER ::= { snFGS624Family 3 }
  snFGS624PPOE         OBJECT IDENTIFIER ::= { snFGS624PPOEFamily 1 }   -- FastIron GS Switch(FGS) 24-port 10/100/1000 POE 
  snFGS624PPOESwitch   OBJECT IDENTIFIER ::= { snFGS624PPOE 1 }         -- snFGS624P-POE switch
  snFGS624PPOERouter   OBJECT IDENTIFIER ::= { snFGS624PPOE 2 }         -- snFGS624P-POE router

  snFGS624XGPPOEFamily OBJECT IDENTIFIER ::= { snFGS624Family 4 }
  snFGS624XGPPOE       OBJECT IDENTIFIER ::= { snFGS624XGPPOEFamily 1 } -- FastIron GS Switch(FGS) 24-port 10/100/1000 POE + 1 10G
  snFGS624XGPPOESwitch OBJECT IDENTIFIER ::= { snFGS624XGPPOE 1 }       -- FGS624XGP-POE switch
  snFGS624XGPPOERouter OBJECT IDENTIFIER ::= { snFGS624XGPPOE 2 }       -- FGS624XGP-POE router

  snFGS648Family       OBJECT IDENTIFIER ::= { snFGSFamily 2 }

  snFGS648PBaseFamily  OBJECT IDENTIFIER ::= { snFGS648Family 1 }
  snFGS648P            OBJECT IDENTIFIER ::= { snFGS648PBaseFamily 1 }  -- FastIron GS Switch(FGS) 48-port 10/100/1000 POE Ready
  snFGS648PSwitch      OBJECT IDENTIFIER ::= { snFGS648P 1 }            -- FGS648P switch
  snFGS648PRouter      OBJECT IDENTIFIER ::= { snFGS648P 2 }            -- FGS648P router

  snFGS648PPOEFamily   OBJECT IDENTIFIER ::= { snFGS648Family 2 }
  snFGS648PPOE         OBJECT IDENTIFIER ::= { snFGS648PPOEFamily 1 }   -- FastIron GS Switch(FGS) 48-port 10/100/1000 POE 
  snFGS648PPOESwitch   OBJECT IDENTIFIER ::= { snFGS648PPOE 1 }         -- snFGS648P-POE switch
  snFGS648PPOERouter   OBJECT IDENTIFIER ::= { snFGS648PPOE 2 }         -- snFGS648P-POE router


  snFLSFamily          OBJECT IDENTIFIER ::= { registration 46 }	-- FastIron LS series family
  snFLS624Family       OBJECT IDENTIFIER ::= { snFLSFamily 1 }

  snFLS624BaseFamily  OBJECT IDENTIFIER ::= { snFLS624Family 1 }
  snFLS624            OBJECT IDENTIFIER ::= { snFLS624BaseFamily 1 }  -- FastIron LS Switch(FLS) 24-port 10/100/1000 
  snFLS624Switch      OBJECT IDENTIFIER ::= { snFLS624 1 }                 -- FLS624 switch
  snFLS624Router      OBJECT IDENTIFIER ::= { snFLS624 2 }                 -- FLS624 router

  snFLS648Family       OBJECT IDENTIFIER ::= { snFLSFamily 2 }

  snFLS648BaseFamily  OBJECT IDENTIFIER ::= { snFLS648Family 1 }
  snFLS648            OBJECT IDENTIFIER ::= { snFLS648BaseFamily 1 }  -- FastIron LS Switch(FLS) 48-port 10/100/1000
  snFLS648Switch      OBJECT IDENTIFIER ::= { snFLS648 1 }               -- FLS648 switch
  snFLS648Router      OBJECT IDENTIFIER ::= { snFLS648 2 }               -- FLS648 router

  snSIFamily           OBJECT IDENTIFIER ::= { registration 47 }     -- ServerIron series family

  snSI100              OBJECT IDENTIFIER ::= { snSIFamily 1 }        -- ServerIron 100 series
  snSI100Switch        OBJECT IDENTIFIER ::= { snSI100 1 }           -- SI100 switch
  snSI100Router        OBJECT IDENTIFIER ::= { snSI100 2 }           -- SI100 router

  snSI350              OBJECT IDENTIFIER ::= { snSIFamily 2 }        -- ServerIron 350 series
  snSI350Switch        OBJECT IDENTIFIER ::= { snSI350 1 }           -- SI350 switch
  snSI350Router        OBJECT IDENTIFIER ::= { snSI350 2 }           -- SI350 router

  snSI450              OBJECT IDENTIFIER ::= { snSIFamily 3 }        -- ServerIron 450 series
  snSI450Switch        OBJECT IDENTIFIER ::= { snSI450 1 }           -- SI450 switch
  snSI450Router        OBJECT IDENTIFIER ::= { snSI450 2 }           -- SI450 router

  snSI850              OBJECT IDENTIFIER ::= { snSIFamily 4 }        -- ServerIron 850 series
  snSI850Switch        OBJECT IDENTIFIER ::= { snSI850 1 }           -- SI850 switch
  snSI850Router        OBJECT IDENTIFIER ::= { snSI850 2 }           -- SI850 router

  snSI350Plus          OBJECT IDENTIFIER ::= { snSIFamily 5 }        -- ServerIron 350 Plus series
  snSI350PlusSwitch    OBJECT IDENTIFIER ::= { snSI350Plus 1 }       -- SI350 Plus switch
  snSI350PlusRouter    OBJECT IDENTIFIER ::= { snSI350Plus 2 }       -- SI350 Plus router

  snSI450Plus          OBJECT IDENTIFIER ::= { snSIFamily 6 }        -- ServerIron 450 Plus series
  snSI450PlusSwitch    OBJECT IDENTIFIER ::= { snSI450Plus 1 }       -- SI450 Plus switch
  snSI450PlusRouter    OBJECT IDENTIFIER ::= { snSI450Plus 2 }       -- SI450 Plus router

  snSI850Plus          OBJECT IDENTIFIER ::= { snSIFamily 7 }        -- ServerIron 850 Plus series
  snSI850PlusSwitch    OBJECT IDENTIFIER ::= { snSI850Plus 1 }       -- SI850 Plus switch
  snSI850PlusRouter    OBJECT IDENTIFIER ::= { snSI850Plus 2 }       -- SI850 Plus router

  snServerIronGTc         OBJECT IDENTIFIER ::= { snSIFamily 8 }         -- ServerIronGT C series
  snServerIronGTcSwitch   OBJECT IDENTIFIER ::= { snServerIronGTc 1 }    -- ServerIronGT C switch
  snServerIronGTcRouter   OBJECT IDENTIFIER ::= { snServerIronGTc 2 }    -- ServerIronGT C router

  snServerIronGTe         OBJECT IDENTIFIER ::= { snSIFamily 9 }         -- ServerIronGT E series
  snServerIronGTeSwitch   OBJECT IDENTIFIER ::= { snServerIronGTe 1 }    -- ServerIronGT E switch
  snServerIronGTeRouter   OBJECT IDENTIFIER ::= { snServerIronGTe 2 }    -- ServerIronGT E router

  snServerIronGTePlus       OBJECT IDENTIFIER ::= { snSIFamily 10 }         -- ServerIronGT E Plus series
  snServerIronGTePlusSwitch OBJECT IDENTIFIER ::= { snServerIronGTePlus 1 } -- ServerIronGT E Plus switch
  snServerIronGTePlusRouter OBJECT IDENTIFIER ::= { snServerIronGTePlus 2 } -- ServerIronGT E Plus router

  snServerIron4G          OBJECT IDENTIFIER ::= { snSIFamily 11 }        -- ServerIron4G series
  snServerIron4GSwitch    OBJECT IDENTIFIER ::= { snServerIron4G 1 }     -- ServerIron4G switch
  snServerIron4GRouter    OBJECT IDENTIFIER ::= { snServerIron4G 2 }     -- ServerIron4G router

-- EdgeIron Stackable family
  edgeIron          OBJECT IDENTIFIER ::= { products 4 }
  edgeIronMib       OBJECT IDENTIFIER ::= { edgeIron 1 }  -- MIB root for EdgeIron family

-- EdgeIron Type 2 Stackable family
  edgeIronType2     OBJECT IDENTIFIER ::= { products 5 }
  edgeIronType2Mib  OBJECT IDENTIFIER ::= { edgeIronType2 1 } -- MIB root for EdgeIron type 2 family

-- IronPoint 200 family
  wirelessAp        OBJECT IDENTIFIER ::= { products 6 } -- wireless access point
  wirelessProbe     OBJECT IDENTIFIER ::= { products 7 } -- wireless probe

-- AccessIron family
  accessIron        OBJECT IDENTIFIER ::= { products 8 }

-- ServerIronSA family
  serverIronSA      OBJECT IDENTIFIER ::= { products 9 }

-- Wireless Application family
  wirelessApplication  OBJECT IDENTIFIER ::= { products 10 }
  wirelessLocation     OBJECT IDENTIFIER ::= { wirelessApplication 1 }
  
-- IronPoint Mobility family
  ironPointMobility  OBJECT IDENTIFIER ::= { products 11 } -- IronPoint Mobility Series
  ironPointMC        OBJECT IDENTIFIER ::= { ironPointMobility 1 } -- IronPoint Mobility Controller

-- NetIron MTU CPE family
  netIronMtuCpeFamily  OBJECT IDENTIFIER ::= { products 12 }
  netIronM2404         OBJECT IDENTIFIER ::= { netIronMtuCpeFamily 1 }

-- IronView family
  ironView             OBJECT IDENTIFIER ::= { products 13 }

-- VENDOR
  digitalChina      OBJECT IDENTIFIER ::= { vendors 1 }

  dcrs7504          OBJECT IDENTIFIER ::= { digitalChina 1 } -- DCRS-7504 family
  dcrs7504Switch    OBJECT IDENTIFIER ::= { dcrs7504 1 }     -- DCRS-7504 switch
  dcrs7504Router    OBJECT IDENTIFIER ::= { dcrs7504 2 }     -- DCRS-7504 router

  dcrs7508          OBJECT IDENTIFIER ::= { digitalChina 2 } -- DCRS-7508 family
  dcrs7508Switch    OBJECT IDENTIFIER ::= { dcrs7508 1 }     -- DCRS-7508 switch
  dcrs7508Router    OBJECT IDENTIFIER ::= { dcrs7508 2 }     -- DCRS-7508 router

  dcrs7515          OBJECT IDENTIFIER ::= { digitalChina 3 } -- DCRS-7515 family
  dcrs7515Switch    OBJECT IDENTIFIER ::= { dcrs7515 1 }     -- DCRS-7515 switch
  dcrs7515Router    OBJECT IDENTIFIER ::= { dcrs7515 2 }     -- DCRS-7515 router

-- Experimental mibs go here.
  experimental           OBJECT IDENTIFIER ::= { foundry 3 }
  pwe3           OBJECT IDENTIFIER ::= { experimental 1 }
  l3vpn           OBJECT IDENTIFIER ::= { experimental 2 }

END
FOUNDRY-SN-AGENT-MIB DEFINITIONS ::= BEGIN

-- BigIron Router Switch Agent MIB Release 2.0.0
-- Revision 10/11/99

-- Copyright 1996 Foundry Networks, Inc.
-- All rights reserved.
-- This Foundry SNMP Management Information Base Specification
-- (Specification) embodies Foundry's confidential and
-- proprietary intellectual property. Foundry retains all
-- title and ownership in the Specification, including any
-- revisions.

-- This Specification is supplied "AS IS," and Foundry makes
-- no warranty, either express or implied, as to the use,
-- operation, condition, or performance of the Specification.

-- SECTION 1: Top Level Definitions

-- Imports

IMPORTS
	TimeTicks, IpAddress, Counter, Gauge
		FROM RFC1155-SMI
	Unsigned32
		FROM SNMPv2-SMI
	OBJECT-TYPE
		FROM RFC-1212
	InterfaceIndex
		FROM IF-MIB
	snChassis, snAgentSys, snStack
		FROM FOUNDRY-SN-ROOT-MIB;


		-- textual conventions

          DisplayString ::=
              OCTET STRING
          -- This data type is used to model textual information taken
          -- from the NVT ASCII character set.  By convention, objects
          -- with this syntax are declared as having
          --
          --      SIZE (0..255)

	  MacAddress ::=
	      OCTET STRING (SIZE(6))
	  -- This data type is used to model media addresses.  For many
	  -- types of media, this will be in a binary representation.
	  -- For example, an ethernet address would be represented as
	  -- a string of 6 octets.

-- Groups

snChasGen	OBJECT IDENTIFIER ::= { snChassis 1 }
snChasPwr	OBJECT IDENTIFIER ::= { snChassis 2 }
snChasFan	OBJECT IDENTIFIER ::= { snChassis 3 }


-- SECTION 2: MIB Objects


-- General Chassis Information

snChasType OBJECT-TYPE
    SYNTAX DisplayString (SIZE(0..128))
	ACCESS	read-only
	STATUS	mandatory
	DESCRIPTION
		"The chassis type represents the type 
		of Foundry product being managed. "
	::= { snChasGen 1 }



snChasSerNum OBJECT-TYPE
	SYNTAX	DisplayString (SIZE(0..128))
	ACCESS	read-only
	STATUS	mandatory
	DESCRIPTION
		"The serial number of the chassis. If the
		serial number is unknown or unavailable then
		the value should be a zero length string."
	::= { snChasGen 2 }



-- Power Supply Status


snChasPwrSupplyStatus OBJECT-TYPE
	SYNTAX	INTEGER
	ACCESS	read-only
	STATUS	mandatory
	DESCRIPTION
		"A bit array that contains the value of the
		Chassis Power Supplies. This is a packed bit string;
		the 2 power supplies status are encoded into 4 bits
		(a nibble). 

		There are multiple power supplies per chassis in this release.
		The following shows the meaning of each bit:
		(bit 0 is the least significant bit).

		  bit position   meaning
		  ------------   -------
			  12-31  reserved
		      11     Power  Supply 4 DC (0=bad, 1=good).
		      10     Power  Supply 3 DC (0=bad, 1=good).
		      9      Power  Supply 4 present status (0=present, 1=not-present).
		      8      Power  Supply 3 present status (0=present, 1=not-present).
			  4-7    reserved
		      3      Power  Supply 2 DC (0=bad, 1=good).
		      2      Power  Supply 1 DC (0=bad, 1=good).
		      1      Power  Supply 2 present status (0=present, 1=not-present).
		      0      Power  Supply 1 present status (0=present, 1=not-present)."
	::= { snChasGen 3 }


-- Fan Status


snChasFanStatus OBJECT-TYPE
	SYNTAX	INTEGER
	ACCESS	read-only
	STATUS	mandatory
	DESCRIPTION
		"A bit array that contains the value of the
		fan status. This is a packed bit string. The
		status of each fan is encoded into one bit.

		  bit value    meaning
		  ---------    -------
		      0         fan failure.
		      1         fan good.

		There are two fans per VLAN Switch chassis in this release.
		The following shows the meaning of each bit:
		(bit 0 is the least significant bit).

		  bit position   meaning
		  ------------   -------
              6-31       reserved
              5          fan6 status
              4          fan5 status
              3          fan4 status
              2          fan3 status
              1          fan2 status
		      0          fan1 status"
	::= { snChasGen 4 }




snChasMainBrdDescription OBJECT-TYPE
    SYNTAX DisplayString (SIZE(0..128))
    ACCESS read-only
    STATUS mandatory
    DESCRIPTION
        "The main board description string. (It is obsoleted for Chassis Product)"
    ::= { snChasGen 5 }


snChasMainPortTotal OBJECT-TYPE
    SYNTAX INTEGER (1..24)
    ACCESS read-only
    STATUS mandatory
    DESCRIPTION
        "The total number of ports for the main board. (It is obsoleted for Chassis Product)"
    ::= { snChasGen 6 }


snChasExpBrdDescription OBJECT-TYPE
    SYNTAX DisplayString (SIZE(0..128))
    ACCESS read-only
    STATUS mandatory
    DESCRIPTION
        "The expansion board description string. Expansion
        board are those boards attaching on the main board.
        (It is obsoleted for Chassis Product)"
    ::= { snChasGen 7 }


snChasExpPortTotal OBJECT-TYPE
	SYNTAX INTEGER (1..24)
    ACCESS read-only
    STATUS mandatory
    DESCRIPTION
        "The total number of ports for the expansion board.
        (It is obsoleted for Chassis Product)"
    ::= { snChasGen 8 }


snChasStatusLeds OBJECT-TYPE
	SYNTAX	INTEGER
	ACCESS	read-only
	STATUS	mandatory
	DESCRIPTION
		"A bit array that contains the value of the
		front panel status LEDs. This is a bit-map; 
		each LED is encoded into 1 bit for each switch
		port.  The maximum number of ports in one chassis 
		is 24 that means 24 Ports Status LEDs. The expansion port 
		number always begins from the last main port number.  
		The following shows the meaning of each bit for each 
		switch port:

		  bit value  meaning
		  --------   ---------  
		     0         off (Link off)
			 1         on  (Link on)

		The bitmap of LEDs are as following: 
			  
                 (Port1)            (Port4)                    (Port8)
        Bit      (Bit0)             (Bit3)                      (Bit7)
		Byte 1:	 LED1	LED2   LED3  LED4   LED5   LED6   LED7   LED8    
		Byte 2:	 LED9	LED10  LED11 LED12  LED13  LED14  LED15  LED16     
		Byte 3:	 LED17	LED18  LED19 LED20  LED21  LED22  LED23  LED24
        --------"
	::= { snChasGen 9 }


snChasTrafficLeds OBJECT-TYPE
	SYNTAX	INTEGER
	ACCESS	read-only
	STATUS	mandatory
	DESCRIPTION
		"A bit array that contains the value of the
		front panel traffic LEDs. This is a packed bit string; 
		each LED is encoded into 1 bit for each switch
		port.  The maximum number of ports in one chassis 
		is 24 that means 24 Ports Traffic LEDs. The expansion port 
		number always begins from the last main port number.  
		The following shows the meaning of each bit for each 
		switch port:

		  bit value  meaning
		  --------   ---------  
		     0         off (no traffic)
			 1         on  (traffic)

		The bitmap of LEDs are as following: 
			  
                 (Port1)            (Port4)                    (Port8)
        Bit      (Bit0)             (Bit3)                      (Bit7)
		Byte 1:	 LED1	LED2   LED3  LED4   LED5   LED6   LED7   LED8    
		Byte 2:	 LED9	LED10  LED11 LED12  LED13  LED14  LED15  LED16     
		Byte 3:	 LED17	LED18  LED19 LED20  LED21  LED22  LED23  LED24
        --------"
	::= { snChasGen 10 }


snChasMediaLeds OBJECT-TYPE
	SYNTAX	INTEGER
	ACCESS	read-only
	STATUS	mandatory
	DESCRIPTION
		"A bit array that contains the value of the
		front panel media LEDs. This is a packed bit string; 
		each LED is encoded into 1 bit for each switch port.  
		The maximum number of ports in one chassis is 24 
		that means 24 Ports Media LEDs.  The expansion port 
		number always begins from the last main port number. 
		The following shows the meaning of each bit for each 
		switch port:

		bit value  meaning   
		---------  -------
      	  0        half duplex
      	  1        full duplex

		The bitmap of LEDs are as following: 
		         (Port1)            (Port4)                    (Port8)
        Bit      (Bit0)             (Bit3)                      (Bit7)
		Byte 1:	 LED1	LED2   LED3  LED4   LED5   LED6   LED7   LED8    
		Byte 2:	 LED9	LED10  LED11 LED12  LED13  LED14  LED15  LED16     
		Byte 3:	 LED17	LED18  LED19 LED20  LED21  LED22  LED23  LED24			  
        ---------"
	::= { snChasGen 11 }


snChasEnablePwrSupplyTrap OBJECT-TYPE
	SYNTAX	INTEGER { disabled(0), enabled(1) }
	ACCESS	read-write
	STATUS	mandatory
	DESCRIPTION
		"Indicates whether the SNMP agent process is
		permitted to generate power supply failure traps."
    DEFVAL { enabled }
	::= { snChasGen 12 }

snChasMainBrdId OBJECT-TYPE
    SYNTAX OCTET STRING
    ACCESS read-only
	STATUS mandatory
	DESCRIPTION
        "The main board identifier, which can uniquely identify a board
        type. It is an encoded octet string with the following meaning:
          octet 0  - octet string format version, which identifies the
                     format of this string.

        If format version octet has the value 1, the octets after the
        version octet have the following meaning:
          octet 1  - product type, FIWG=0x57, FIBB=0x42, FIMLS=0x4D
                     NI=0x4E, TI=0x54, TIRT=0x52
          octet 2  - board type, POWERPC=1, ALPHA=2
		  The length of the octet string is 27.

        If format version octet has the value 2, the octets after the
        version octet have the following meaning:
          octet 1  - product type: 
						BI_WG					0x57
						BI_BB					0x42
						BI_NI					0x4E
						NI_M4					0x4D
						BI_SLB					0x53
          octet 2  - module type:
						MASTER_FIBER_8G			0x0
						MASTER_FIBER_4G			0x1
						MASTER_COPPER_16		0x2
						SLAVE_FIBER_4G			0x3
						FI_MASTER_FIBER_2G		0x4
						FI_MASTER_FIBER_4G		0x5
						MASTER_COPPER_8G		0x6
						FI_MASTER_FIBER_8G		0x7
						SLAVE_FIBER_8G			0x8
						MASTER_COPPER_12_2		0x9
						SLAVE_COPPER_24			0xA
						FI_SLAVE_COPPER_24		0xB
						SLAVE_100FX_8			0xD
						SLAVE_100FX_16			0xC
						SLAVE_COPPER_8G			0xE
						SLAVE_COPPER_16_2		0xF
						STACK_FIBER_8G			0x10
						STACK_COPPER_8G			0x11
						MASTER_FIBER_2G			0x12	
						SLAVE_100FX_24			0x13
						MASTER_FIBER_0G			0x14	
						POS_622M				0x15
						POS_155M				0x16
						SLAVE_FIBER_2G			0x17
						SLAVE_COPPER_2G			0x18
						FI_SLAVE_FIBER_2G		0x19
						FI_SLAVE_FIBER_4G		0x1A
						FI_SLAVE_FIBER_8G		0x1B
						FI_SLAVE_COPPER_8G		0x1C
						FI_MASTER_COPPER_8G		0x1D
						POS_155M2P				0x1E
						FI_MASTER_COPPER_4G		0x1F
						FI_MASTER_COPPER_2G		0x20
						MASTER_COPPER_4G		0x21
						MASTER_COPPER_2G		0x22
						MASTER_M4_8G			0x23
						MASTER_M4_4G			0x24
						MASTER_M4_2G			0x25
						MASTER_M4_0G			0x26	
						MASTER_M5_0G			0x27	
						POS_2488M				0x28	
						SLAVE_M5_0G				0x29	
						POS_N2488M				0x2A	
						STACK_IPC_48_2			0x2B	
						SLAVE_NPA_FIBER_4G		0x2C	
						ATM_2PORT				0x2D	
						ATM_4PORT				0x2E	
						SLAVE_FIBER_10G			0x2F
						STACK_FES_48_2			0x30
						STACK_FES_24_2			0x31
						STACK_FES_96_4			0x32
						STACK_FES_12G			0x33
						STACK_FESX_24G			0x34
						STACK_FESX_24_2_G		0x35
						STACK_FESX_24_1_G		0x36
						STACK_FESX_48G			0x37
						STACK_FESX_48_2_G		0x38
						STACK_FESX_48_1_G		0x39
						SUPERX_FI_MGMT		    0x40
						SUPERX_FI_2P10G 		0x41
						SUPERX_FI_24GC  		0x42
						SUPERX_FI_24GF  		0x43
						SUPERX_FI_2P10G_WAN 	0x44
						SUPERX_FI_MGMT_II       0x4a
						SLAVE_JC_48E			0xC3	
						SLAVE_JC_48T			0xC4	
						MASTER_JC_M4_8G		0xC5
						SLAVE_JC_8G				0xC6	
						SLAVE_JC_B16GF			0xC8	
						MASTER_JC_B2404			0xC9	
						SLAVE_JC_B16GC			0xCA	

		  The length of the octet string is 28.

          Both format version 1 and 2:
          octet 3  - processor type, PVR_M603=3, PVR_M604=4, PVR_M603E=6,
                     PVR_M603EV=7, PVR_M750=8, PVR_M604E=9, PVR_M8245=81
          octet 4 to
          octet 5  - processor speed in MHz
          octet 6  - MAC type:
          				MAC_NONE=0
          				MAC_SEEQ_10_100=1, 
          				MAC_DEC_10_100=2,
          				MAC_3COM_10_100=3,
						MAC_X10GMAC_10000=4,
                     	MAC_SEEQ_1000=5, 
						MAC_GMAC_1000=6,
						MAC_VLSI_1000=7
          octet 7  - PHY type, PHY_NONE=0, PHY_QSI=1, PHY_BROADCOM=2,
                     PHY_ICS=3, PHY_NATIONAL=4, PHY_LEVEL1=6,
                     PHY_BROADCOM_10_100=7, PHY_LEVEL24=8,
                     PHY_BROADCOM_10000=9 (for 10G),
                     PHY_3COM_10_100=9 (for others)
          octet 8  - port type, COPPER=0, FIBER=1
          octet 9  - fiber port type, NONFIBER=0, SX_FIBER=1,
                     LX_FIBER=2, LHX_FIBER=3, LX_SX_FIBER=4,
                     LHB_FIBER=5
          octet 10 to
          octet 13 - DRAM size in KBytes
          octet 14 to
          octet 17 - boot flash size in KBytes
          octet 18 to
          octet 21 - code flash size in KBytes
          octet 22 to
          octet 27 - serial number.

		  Format version 1 only:
          octet 28 - chassis backplane type. 
		 	chassis4000	= 	0x00
		 	chassis8000	=	0x02
		 	chassis15000	=	0x01
		 	chassisFISX	=	0x04
		 	Turbo8			=	0x07 (stack2)
		 	FastIron2		=	0x06 (stack1)"
	::= { snChasGen 13 }


snChasExpBrdId OBJECT-TYPE
    SYNTAX OCTET STRING
    ACCESS read-only
    STATUS mandatory
    DESCRIPTION
        "The expansion board identifier. Expansion board are those
        boards attaching on the main board. It is an encoded octet
		string with the following meaning:
          octet 0  - octet string format version, which identifies
                     the format of this string.
        If format version octet has the value 1, the octets after
        the version octet have the following meaning:
          octet 1  - expansion board type, HUNDRED_MEG_1PORT=1,
                     HUNDRED_MEG_2PORT=2, HUNDRED_MEG_1PORT_COPPER=3,
                     HUNDRED_MEG_2PORT_COPPER=4, HUNDRED_MEG_2PORT_LX=5,
                     GIGA_1PORT=8, GIGA_2PORT=9
          octet 2  - fiber port type, NONFIBER=0, SX_FIBER=1,
                     LX_FIBER=2, LHX_FIBER=3, LX_SX_FIBER=4
        (It is obsoleted for Chassis Product)"
    ::= { snChasGen 14 }


snChasSpeedLeds OBJECT-TYPE
	SYNTAX	INTEGER
	ACCESS	read-only
	STATUS	mandatory
	DESCRIPTION
		"A bit array that contains the value of the
		front panel media LEDs. This is a packed bit string; 
		each LED is encoded into 1 bit for each switch port.  
		The maximum number of ports in one chassis is 24 
		that means 24 Ports Speed LEDs.  The expansion port 
		number always begins from the last main port number. 
		The following shows the meaning of each bit for each 
		switch port:

		bit value  meaning   
		---------  -------
      	  0        10 MBit
      	  1        100 MBit

		The bitmap of LEDs are as following: 
		         (Port1)            (Port4)                    (Port8)
        Bit      (Bit0)             (Bit3)                      (Bit7)
		Byte 1:	 LED1	LED2   LED3  LED4   LED5   LED6   LED7   LED8    
		Byte 2:	 LED9	LED10  LED11 LED12  LED13  LED14  LED15  LED16     
		Byte 3:	 LED17	LED18  LED19 LED20  LED21  LED22  LED23  LED24			  
        ---------"
	::= { snChasGen 15 }


snChasEnableFanTrap OBJECT-TYPE
	SYNTAX	INTEGER { disabled(0), enabled(1) }
	ACCESS	read-write
	STATUS	mandatory
	DESCRIPTION
		"Indicates whether the SNMP agent process is
		permitted to generate fan failure traps."
    DEFVAL { enabled }
	::= { snChasGen 16 }


snChasIdNumber OBJECT-TYPE
    SYNTAX  DisplayString (SIZE (0..64))
    ACCESS  read-write
    STATUS  mandatory
    DESCRIPTION
        "An administratively-assigned chassis identity number,
        used by inventory control."
    ::= { snChasGen 17 }


snChasActualTemperature OBJECT-TYPE
    SYNTAX  INTEGER (-110..250)
	ACCESS	read-only
	STATUS	mandatory
	DESCRIPTION
		"Temperature of the chassis. Each unit is 0.5 degrees Celcius.
		Only management module built with temperature sensor hardware
		is applicable. For those non-applicable management module, it
		returns no-such-name."
	::= { snChasGen 18 }


snChasWarningTemperature OBJECT-TYPE
    SYNTAX  INTEGER (0..250)
	ACCESS	read-write
	STATUS	mandatory
	DESCRIPTION
		"Actual temperature higher than this threshold value will trigger
		the switch to send a temperature warning trap. Each unit is 0.5
		degrees Celcius. Only management module built with temperature
		sensor hardware is applicable. For those non-applicable management
		module, it returns no-such-name."
	::= { snChasGen 19 }


snChasShutdownTemperature OBJECT-TYPE
    SYNTAX  INTEGER (0..250)
	ACCESS	read-write
	STATUS	mandatory
	DESCRIPTION
		"Actual temperature higher than this threshold value will shutdown
		a partial of the switch hardware to cool down the system. Each unit
		is 0.5 degrees Celcius. Only management module built with temperature
		sensor hardware is applicable. For those non-applicable management
		module, it returns no-such-name."
	::= { snChasGen 20 }

snChasEnableTempWarnTrap OBJECT-TYPE
	SYNTAX	INTEGER { disabled(0), enabled(1) }
	ACCESS	read-write
	STATUS	mandatory
	DESCRIPTION
		"Indicates whether the SNMP agent process is
		permitted to generate temperature warning traps."
    DEFVAL { enabled }
	::= { snChasGen 21 }

-- Flash Card

snChasFlashCard OBJECT-TYPE
	SYNTAX	INTEGER
	ACCESS	read-only
	STATUS	mandatory
	DESCRIPTION
		"A bit array that contains the value of the
		flash card status. This is a packed bit string. The
		status of each flash card is encoded into one bit.

		  bit value    meaning
		  ---------    -------
		      0         flash card absent.
		      1         flash card present.

		There are up to two flash cards in this release.
		This object is valid if M4 management module is present.
		The following shows the meaning of each bit:
		(bit 0 is the least significant bit).

		  bit position   meaning
		  ------------   -------
              2-31       reserved
              1          flash card 2 status
		      0          flash card 1 status"
	::= { snChasGen 22 }


snChasFlashCardLeds OBJECT-TYPE
	SYNTAX	INTEGER
	ACCESS	read-only
	STATUS	mandatory
	DESCRIPTION
		"A bit array that contains the value of the
		flash card LEDs. This is a packed bit string; 
		each LED is encoded into 1 bit for each flash card.

		  bit value  meaning
		  --------   ---------  
		     0         off 
			 1         on 
		"	  
	::= { snChasGen 23 }


snChasNumSlots OBJECT-TYPE
	SYNTAX	INTEGER
	ACCESS	read-only
	STATUS	mandatory
	DESCRIPTION
		"Number of slots of the chassis."
	::= { snChasGen 24 }


snChasArchitectureType OBJECT-TYPE
	SYNTAX	INTEGER
	ACCESS	read-only
	STATUS	mandatory
	DESCRIPTION
		"Architecture type."
	::= { snChasGen 25 }


snChasProductType OBJECT-TYPE
	SYNTAX	INTEGER
	ACCESS	read-only
	STATUS	mandatory
	DESCRIPTION
		"Product type."
	::= { snChasGen 26 }


-- Power Supply Table


snChasPwrSupplyTable OBJECT-TYPE
	SYNTAX	SEQUENCE OF SnChasPwrSupplyEntry
	ACCESS	not-accessible
	STATUS	mandatory
	DESCRIPTION
		"A table of each power supply information. Only installed
		power supply appears in a table row."
	::= { snChasPwr 1 }

snChasPwrSupplyEntry OBJECT-TYPE
	SYNTAX	SnChasPwrSupplyEntry
	ACCESS	not-accessible
	STATUS	mandatory
	DESCRIPTION
		"A row in the power supply table."
	INDEX	{ snChasPwrSupplyIndex }
	::= { snChasPwrSupplyTable 1 }

SnChasPwrSupplyEntry ::= SEQUENCE {
	snChasPwrSupplyIndex
		INTEGER,
	snChasPwrSupplyDescription
		DisplayString,
	snChasPwrSupplyOperStatus
		INTEGER
	}

snChasPwrSupplyIndex OBJECT-TYPE
	SYNTAX	INTEGER
	ACCESS	read-only
	STATUS	mandatory
	DESCRIPTION
		"The index to power supply table."
	::= { snChasPwrSupplyEntry 1 }

snChasPwrSupplyDescription OBJECT-TYPE
    SYNTAX DisplayString (SIZE(0..128))
    ACCESS read-only
    STATUS mandatory
    DESCRIPTION
        "The power supply description string."
    ::= { snChasPwrSupplyEntry 2 }

snChasPwrSupplyOperStatus OBJECT-TYPE
	SYNTAX  INTEGER {
		other(1),
		normal(2),
		failure(3)
		}
	ACCESS  read-only
	STATUS  mandatory
	DESCRIPTION
		"The power supply operation status."
    ::= { snChasPwrSupplyEntry 3 }


-- Fan Table


snChasFanTable OBJECT-TYPE
	SYNTAX	SEQUENCE OF SnChasFanEntry
	ACCESS	not-accessible
	STATUS	mandatory
	DESCRIPTION
		"A table of each fan information. Only installed
		fan appears in a table row."
	::= { snChasFan 1 }

snChasFanEntry OBJECT-TYPE
	SYNTAX	SnChasFanEntry
	ACCESS	not-accessible
	STATUS	mandatory
	DESCRIPTION
		"A row in the fan table."
	INDEX	{ snChasFanIndex }
	::= { snChasFanTable 1 }

SnChasFanEntry ::= SEQUENCE {
	snChasFanIndex
		INTEGER,
	snChasFanDescription
		DisplayString,
	snChasFanOperStatus
		INTEGER
	}

snChasFanIndex OBJECT-TYPE
	SYNTAX	INTEGER
	ACCESS	read-only
	STATUS	mandatory
	DESCRIPTION
		"The index to fan table."
	::= { snChasFanEntry 1 }

snChasFanDescription OBJECT-TYPE
    SYNTAX DisplayString (SIZE(0..128))
    ACCESS read-only
    STATUS mandatory
    DESCRIPTION
        "The fan description string."
    ::= { snChasFanEntry 2 }

snChasFanOperStatus OBJECT-TYPE
	SYNTAX  INTEGER {
		other(1),
		normal(2),
		failure(3)
		}
	ACCESS  read-only
	STATUS  mandatory
	DESCRIPTION
		"The fan operation status."
    ::= { snChasFanEntry 3 }


-- Agent Groups

snAgentGbl				OBJECT IDENTIFIER ::= { snAgentSys 1 }
snAgentBrd				OBJECT IDENTIFIER ::= { snAgentSys 2 }
snAgentTrp 				OBJECT IDENTIFIER ::= { snAgentSys 3 }
snAgentBoot				OBJECT IDENTIFIER ::= { snAgentSys 4 }
snAgCfgEos				OBJECT IDENTIFIER ::= { snAgentSys 5 }
snAgentLog				OBJECT IDENTIFIER ::= { snAgentSys 6 }
snAgentSysParaConfig	OBJECT IDENTIFIER ::= { snAgentSys 7 }
snAgentConfigModule		OBJECT IDENTIFIER ::= { snAgentSys 8 }
snAgentUser				OBJECT IDENTIFIER ::= { snAgentSys 9 }
snAgentRedundant		OBJECT IDENTIFIER ::= { snAgentSys 10 }
snAgentCpu			    OBJECT IDENTIFIER ::= { snAgentSys 11 }
snAgentHw			    OBJECT IDENTIFIER ::= { snAgentSys 12 }
snAgentTemp			    OBJECT IDENTIFIER ::= { snAgentSys 13 }
snAgentPoe				OBJECT IDENTIFIER ::= { snAgentSys 14 }

-- SECTION 2: MIB Objects


-- Agent's Global Group
	
snAgReload OBJECT-TYPE
	SYNTAX	INTEGER {
		other(1),
		running(2),
		reset(3),
		busy(4)
		}
	ACCESS	read-write
	STATUS	mandatory
	DESCRIPTION
		"Action object to reboot the agent.
		The following values can only be read:
		  other(1).....agent in unknown or other state
		  running(2)...agent running
		  busy(4).......reload not allowed at this time, flash is busy

		The following value can be written:
		  reset(3).....do a hard reset

		The agent will return a
		response before the action occurs."
	::= { snAgentGbl 1 }

snAgEraseNVRAM OBJECT-TYPE
	SYNTAX	INTEGER {
		normal(1),
		error(2),
		erase(3),
		erasing(4),		
		busy(5)
		}
	ACCESS	read-write
	STATUS	mandatory
	DESCRIPTION
		"Action object to erase NVRAM of the agent.
		The following values can only be read:
		  normal(1)
		  error(2)... operation failed or bad flash
		  erasing(4)...agent is erasing NVRAM flash
		  busy(5).......operation not allowed at this time, flash is busy

		The following value can be written:
		  erase(3).....do erase 

		The agent will return a response even before the erase is done.
		And the read value will be erasing until erase is done.
		And the erase request will be rejected until error or normal."
	::= { snAgentGbl 2 }

snAgWriteNVRAM OBJECT-TYPE
	SYNTAX	INTEGER {
		normal(1),
		error(2),
		write(3),
		writing(4),		
		busy(5)
		}
	ACCESS	read-write
	STATUS	mandatory
	DESCRIPTION
		"Action object to save all configuration info to
		 NVRAM of the agent.
		The following values can only be read:
		  normal(1)
		  error(2)... operation failed or bad flash
	  	  writing(4)...agent is writing NVRAM flash
		  busy(5).......operation not allowed at this time, flash is busy

		The following value can be written:
		  write(3).....do write 

		The agent will return a response even before the write is done.
		And the read value will be writing until write is done.
		And the write request will be rejected until error or normal."
	::= { snAgentGbl 3 }

snAgConfigFromNVRAM OBJECT-TYPE
	SYNTAX	INTEGER {
		normal(1),
		error(2),
		config(3),
		configing(4),
		busy(5)
	}
	ACCESS	not-accessible
	STATUS	mandatory
	DESCRIPTION
		"Action object to config the switch from NVRAM of the agent.
		The following values can only be read:
		  normal(1)
		  error(2)... operation failed or bad flash
		  configing(4)...configing from NVRAM flash is in process.
		  busy(5).......operation not allowed at this time, flash is busy
		The following value can be written:
		  config(3).....do config 

		The agent will return a response after config is done."
	::= { snAgentGbl 4 }

--  image and config file down/up load 

snAgTftpServerIp OBJECT-TYPE
	SYNTAX	IpAddress
	ACCESS	read-write
	STATUS	mandatory
	DESCRIPTION
		"The tftp server address, this will be used for both download/upload
		 image file and config file."
	::= { snAgentGbl 5 }

snAgImgFname OBJECT-TYPE
	SYNTAX	DisplayString (SIZE (0..32))
	ACCESS	read-write
	STATUS	mandatory
	DESCRIPTION
		"Name of the image file including path currently associated
		with the system. When the object is not used, the value is a
		zero length string."
	::= { snAgentGbl 6 }


snAgImgLoad OBJECT-TYPE
	SYNTAX	INTEGER {
		normal(1),
		flashPrepareReadFailure(2),
		flashReadError(3),
		flashPrepareWriteFailure(4),
		flashWriteError(5),
		tftpTimeoutError(6),
		tftpOutOfBufferSpace(7),
		tftpBusy(8),
	    tftpRemoteOtherErrors(9), 
	    tftpRemoteNoFile(10), 
	    tftpRemoteBadAccess(11), 
	    tftpRemoteDiskFull(12), 
	    tftpRemoteBadOperation(13), 
	    tftpRemoteBadId(14), 
	    tftpRemoteFileExists(15), 
	    tftpRemoteNoUser(16), 
		operationError(17),
		loading(18),
		uploadMPPrimary(19),
		downloadMPPrimary(20),
		uploadMPSecondary(21),
		downloadMPSecondary(22),
		tftpWrongFileType(23),
		downloadSPPrimary(24),
		downloadSPSecondary(25),
		uploadMPBootROM(26),
		downloadMPBootROM(27),
		uploadMPBootTFTP(28),
		downloadMPBootTFTP(29),
		uploadMPMonitor(30),
		downloadMPMonitor(31),
		downloadSPBootROM(32)
		}
	ACCESS	read-write
	STATUS	mandatory
	DESCRIPTION
		"Action object to down/up load a new image
		to the agent. The following values:
		Error values: from normal(1) to operationError(17) and tftpWrongFileType(23).
		  loading(18) .. operation is in process.

		The following values are used for set :
		  uploadMPPrimary(19)..upload the Primary image from MP flash to tftp server.
		  downloadMPPrimary(20)..download the Primary image from tftp server to MP flash.
		  uploadMPSecondary(21)..upload the Secondary image from MP flash to tftp server.
		  downloadMPSecondary(22)..download the Secondary image from tftp server to MP flash.
		  downloadSPPrimary(24)..download the Primary image from tftp server to SP flash.
		  downloadSPSecondary(25)..download the Secondary image from tftp server to SP flash.
		  uploadMPBootROM(26)..upload the Boot from flash image from MP flash to tftp server.
		  downloadMPBootROM(27)..download the Boot from flash image from tftp server to MP flash.
		  uploadMPBootTFTP(28)..upload the Boot from TFTP image from MP flash to tftp server.
		  downloadMPBootTFTP(29)..download the Boot from TFTP image from tftp server to MP flash.
		  uploadMPMonitor(30)..upload the Monitor image from MP flash to tftp server.
		  downloadMPMonitor(31)..download the Monitor image from tftp server to MP flash.
		  downloadSPBootROM(32)..download the Boot image from tftp server to SP flash.

		MP is the management processor, SP is the switch processor.

		The image filename is defined in
		snAgImgFname. The tftp server address is defined in snAgTftpServerIp.
		Atomic set of snAgImgLoad, snAgImgFname and  
		snAgTftpServerIp is required to allow down/up load to happen. 
		And the write request will be rejected during loading until error 
		or normal."
	::= { snAgentGbl 7 }

snAgCfgFname OBJECT-TYPE
	SYNTAX	DisplayString (SIZE (0..32))
	ACCESS	read-write
	STATUS	mandatory
	DESCRIPTION
		"Name of the config file(s) including path currently associated
		with the system. Some agents in special
		situations may support a value which contains
		multiple file names instead of a single file
		name. Multiple names are specified as a list
		of file names separated by semicolons (;).
		When the object is not used, the value is a
		zero length string."
	::= { snAgentGbl 8 }

snAgCfgLoad OBJECT-TYPE
	SYNTAX	INTEGER {
		normal(1),
		flashPrepareReadFailure(2),
		flashReadError(3),
		flashPrepareWriteFailure(4),
		flashWriteError(5),
		tftpTimeoutError(6),
		tftpOutOfBufferSpace(7),
		tftpBusy(8),
	    tftpRemoteOtherErrors(9), 
	    tftpRemoteNoFile(10), 
	    tftpRemoteBadAccess(11), 
	    tftpRemoteDiskFull(12), 
	    tftpRemoteBadOperation(13), 
	    tftpRemoteBadId(14), 
	    tftpRemoteFileExists(15), 
	    tftpRemoteNoUser(16), 
		operationError(17),
		loading(18),
		uploadFromFlashToServer(20),
		downloadToFlashFromServer(21),
		uploadFromDramToServer(22),
		downloadToDramFromServer(23),
		uploadFromFlashToNMS(24),
		downloadToFlashFromNMS(25),
		uploadFromDramToNMS(26),
		downloadToDramFromNMS(27),
		operationDoneWithNMS(28),
		tftpWrongFileType(29),
		downloadToDramFromServerOverwrite(30)
		}
	ACCESS	read-write
	STATUS	mandatory
	DESCRIPTION
		"Action object to down/up load a config image
		to the agent. The following values can be
		read :
		Error values: from normal(1) to operationError(17) and tftpWrongFileType(29).
		  loading(18) .. operation is in process.


		The following value can be used to set:
		  uploadFromFlashToServer(20)..upload the config from flash
                                              to tftp server. 
		  downloadToFlashFromServer(21)..download the config to flash
                                                from tftp server.
		  uploadFromDramToServer(22)..upload the config from DRAM 
                                             to tftp server.
		  downloadToDramFromServer(23)..download the config to DRAM
                                               from tftp server.
		  downloadToDramFromServerOverwrite(30)..download the config to DRAM
                                               from tftp server, clear the running-config,
                                               and overwrite with the new config.

		The following value can be used to set:
		  uploadFromFlashToNMS(24)..upload the config from flash to NMS. 
		  downloadToFlashFromNMS(25)..download the config to flash from NMS.
		  uploadFromDramToNMS(26)..upload the config from DRAM to NMS.
		  downloadToDramFromNMS(27)..download the config to DRAM from NMS.

		The config filename is defined in
		snAgCfgFname. The tftp server address is defined in snAgTftpServerIp.
		Atomic set of snAgCfgLoad, snAgCfgFname and  snAgTftpServerIp is
		required to allow down/up load to happen. And the write request 
		will be rejected during loading until error or normal.
		For those NMS commands from (24) to (27), The snAgCfgEosTable MIB must
		be sent along in one PDU.  A seperate write memory cli or set 
		snAgWriteNVRAM is required to save the config to NVRAM."
	::= { snAgentGbl 9 }

-- default gateway ip address

snAgDefGwayIp OBJECT-TYPE
	SYNTAX	IpAddress
	ACCESS	read-write
	STATUS	mandatory
	DESCRIPTION
		"The default gateway (router) address." 	
	::= { snAgentGbl 10 }


-- image version

snAgImgVer OBJECT-TYPE
	SYNTAX	DisplayString (SIZE(0..32))
	ACCESS	read-only
	STATUS	mandatory
	DESCRIPTION
		"The version of the running software in the form
		'major.minor.maintenance[letters]'."
	::= { snAgentGbl 11 }

snAgFlashImgVer OBJECT-TYPE
	SYNTAX	DisplayString (SIZE(0..32))
	ACCESS	read-only
	STATUS	mandatory
	DESCRIPTION
		"The version of the software image saved in local
		storage such as flash memory in the form
		'major.minor.maintenance[letters]'. If not
		known or not available, then the value is
		a zero length string."
	::= { snAgentGbl 12 }

snAgGblIfIpAddr OBJECT-TYPE
	SYNTAX	IpAddress
	ACCESS	read-write
	STATUS	mandatory
	DESCRIPTION
		"The interface ip address."
	::= { snAgentGbl 13 }

snAgGblIfIpMask OBJECT-TYPE
	SYNTAX	IpAddress
	ACCESS	read-write
	STATUS	mandatory
	DESCRIPTION
		"The interface ip address mask."
	::= { snAgentGbl 14 }

snAgGblPassword OBJECT-TYPE
	SYNTAX	DisplayString (SIZE (0..48))
	ACCESS	read-write
	STATUS	mandatory
	DESCRIPTION
		"System Security Access Password and this is only 
		 allowed to use for setting but not for reading.
		 An SNMP-Get will get an zero string."
	::= { snAgentGbl 15 }

snAgTrpRcvrCurEntry OBJECT-TYPE
	SYNTAX	INTEGER (0..255)
	ACCESS	read-only
	STATUS	mandatory
	DESCRIPTION
		"The current total entries of the Trap 
		Receiver Table are created."
	::= { snAgentGbl 16 }

snAgGblDataRetrieveMode OBJECT-TYPE
	SYNTAX  INTEGER {
		nextbootCfg(0),             
		operationalData(1)
		}
	ACCESS  read-write
	STATUS  mandatory
	DESCRIPTION
		"By default, this mode is set to nextbootCfg(0).
		 The VLAN Table and Port-STP Table data will be retrieved
		 according to this mode.
		 nextbootCfg(0).........the nextboot configuration data are retrieved
		 operationalData(1)..........the current running data are retrieved"  
	::= { snAgentGbl 19 }


snAgSystemLog OBJECT-TYPE
	SYNTAX	OCTET STRING (SIZE(5))	
	ACCESS	read-write
	STATUS	mandatory
	DESCRIPTION
		"The system log object to indicate whether any Network
		 Management Station(NMS) has login.  The first byte
		 of the octet string is the value decribed below and 
		 followed by 4 bytes of secret code.
		  login(1)..... a value for a NMS to login.
		  heartbeat(2)... a value for the login NMS periodically to 
		                checkin; Otherwise, the Agent will automatically
		                set this object to logout(3) after a timeout 
		                period. 
		  logout(3).... a value for a NMS to logout.
		  changePassword(4).... a value for the login NMS to change
		                password, only if snAgGblPasswordChangeMode
						was configured to 'anyMgmtEntity'.
		  changeReadOnlyCommunity(5).... a value for the login NMS
		                to change the read-only community string,
		                only if snAgGblPasswordChangeMode was
		                configured to 'anyMgmtEntity'.
		  changeReadWriteCommunity(6).... a value for the login NMS
		                to change the read-write community string,
		                only if snAgGblPasswordChangeMode was
		                configured to 'anyMgmtEntity'."
	::= { snAgentGbl 20 }


snAgGblEnableColdStartTrap OBJECT-TYPE
	SYNTAX	INTEGER { disabled(0), enabled(1) }
	ACCESS	read-write
	STATUS	mandatory
	DESCRIPTION
		"Indicates whether the SNMP agent process is
		permitted to generate cold start traps."
    DEFVAL { enabled }
	::= { snAgentGbl 21 }


snAgGblEnableLinkUpTrap OBJECT-TYPE
	SYNTAX	INTEGER { disabled(0), enabled(1) }
	ACCESS	read-write
	STATUS	mandatory
	DESCRIPTION
		"Indicates whether the SNMP agent process is
		permitted to generate link up traps."
    DEFVAL { enabled }
	::= { snAgentGbl 22 }


snAgGblEnableLinkDownTrap OBJECT-TYPE
	SYNTAX	INTEGER { disabled(0), enabled(1) }
	ACCESS	read-write
	STATUS	mandatory
	DESCRIPTION
		"Indicates whether the SNMP agent process is
		permitted to generate link down traps."
    DEFVAL { enabled }
	::= { snAgentGbl 23 }

snAgGblPasswordChangeMode OBJECT-TYPE
	SYNTAX	INTEGER {
              anyMgmtEntity(1),
              consoleAndTelnet(2),
              consoleOnly(3),
              telnetOnly(4) }
	ACCESS	read-only
	STATUS	mandatory
	DESCRIPTION
		"Specify which management entity is allowed to change
		the password. 'anyMgmtEntity' management entities are
		SNMP management station, console command line interface,
		and telnet command line interface. For security reason,
		this object can only be modified by console command line
		interface or telnet command line interface. The default
		value is 'consoleAndTelnet', of which both console and
		telnet command line interfaces are allowed to change
		the password."
	::= { snAgentGbl 24 }

snAgGblReadOnlyCommunity OBJECT-TYPE
	SYNTAX	DisplayString (SIZE (0..32))
	ACCESS	read-write
	STATUS	mandatory
	DESCRIPTION
		"SNMP read community string and this is only allowed
		to use for setting but not for reading. An SNMP-Get
		will get an zero length string."
	::= { snAgentGbl 25 }

snAgGblReadWriteCommunity OBJECT-TYPE
	SYNTAX	DisplayString (SIZE (0..32))
	ACCESS	read-write
	STATUS	mandatory
	DESCRIPTION
		"SNMP read-write community string and this is only
		allowed to use for setting but not for reading. An
		SNMP-Get will get an zero length string."
	::= { snAgentGbl 26 }

snAgGblCurrentSecurityLevel OBJECT-TYPE
	SYNTAX	INTEGER (0..5)
	ACCESS	read-only
	STATUS	mandatory
	DESCRIPTION
		"This represnts the current log-in security level.
		Each level of security requires a password to permit
		user for different system configurations."
	::= { snAgentGbl 27 }

snAgGblSecurityLevelSet OBJECT-TYPE
	SYNTAX	INTEGER (0..5)
	ACCESS	read-write
	STATUS	mandatory
	DESCRIPTION
		"This shows which the security level password to be set."
	::= { snAgentGbl 28 }

snAgGblLevelPasswordsMask OBJECT-TYPE
	SYNTAX	INTEGER 
	ACCESS	read-only
	STATUS	mandatory
	DESCRIPTION
		"This shows the bitmap of level passwords which successfully assigned to the system."
	::= { snAgentGbl 29 }

snAgGblQueueOverflow OBJECT-TYPE
	SYNTAX	INTEGER	{ false(0), true(1) } 
	ACCESS	read-only
	STATUS	mandatory
	DESCRIPTION
		"false - The device queues are not overflow.
		 true  - The device queues are overflow."
	::= { snAgentGbl 30 }

snAgGblBufferShortage OBJECT-TYPE
	SYNTAX	INTEGER	{ false(0), true(1) } 
	ACCESS	read-only
	STATUS	mandatory
	DESCRIPTION
		"false - The device buffers are adequate.
		 true  - The device buffers are in shortage."
	::= { snAgentGbl 31 }

snAgGblDmaFailure OBJECT-TYPE
	SYNTAX	INTEGER	{ false(0), true(1) } 
	ACCESS	read-only
	STATUS	mandatory
	DESCRIPTION
		"false - The device DMAs are in good condition.
		 true  - One of the DMAs in the device fails."
	::= { snAgentGbl 32 }

snAgGblResourceLowWarning OBJECT-TYPE
	SYNTAX	INTEGER	{ false(0), true(1) } 
	ACCESS	read-only
	STATUS	mandatory
	DESCRIPTION
		"false - No, the device does not have resource-low-warning.
		 true  - Yes, the device does have resource-low-warning."
	::= { snAgentGbl 33 }

snAgGblExcessiveErrorWarning OBJECT-TYPE
	SYNTAX	INTEGER	{ false(0), true(1) } 
	ACCESS	read-only
	STATUS	mandatory
	DESCRIPTION
		"false - No, the device does not have any excessive collision, FCS errors, alignment warning etc.
		 true  - Yes, the device does have."
	::= { snAgentGbl 34 }

snAgGblCpuUtilData OBJECT-TYPE
	SYNTAX	Gauge
	ACCESS	read-only
	STATUS	mandatory
	DESCRIPTION
		"The statistics collection of utilization of the CPU in the device. Reading this object resets all the counters.  Therefore, a user need not set snAgGblUtilCollect."
	::= { snAgentGbl 35 }

snAgGblCpuUtilCollect OBJECT-TYPE
	SYNTAX	INTEGER { disabled(0), enabled(1) }
	ACCESS	read-write
	STATUS	deprecated
	DESCRIPTION
		"enable(1)  - The beginning of statistics collection of utilization of the CPU in the device.
		 disable(0) - The end of statistics collection of utilization of the CPU in the device.
               This object is deprecated. User need not set this object. User can read snAgGblCpuUtilData to reset all the counters. "
	::= { snAgentGbl 36 }

snAgGblTelnetTimeout OBJECT-TYPE
	SYNTAX	INTEGER (0..240)
	ACCESS	read-write
	STATUS	mandatory
	DESCRIPTION
		"Telnet session idling timeout value. Writing value 0 to
		this object never timeouts any telnet sessions. Each value
		unit is one minute."
	::= { snAgentGbl 37 }

snAgGblEnableWebMgmt OBJECT-TYPE
	SYNTAX	INTEGER { disabled(0), enabled(1) }
	ACCESS	read-write
	STATUS	mandatory
	DESCRIPTION
		"Enable/disable web management."
    DEFVAL { enabled }
	::= { snAgentGbl 38 }

snAgGblSecurityLevelBinding OBJECT-TYPE
	SYNTAX	INTEGER
	ACCESS	read-only
	STATUS	mandatory
	DESCRIPTION
		"This represnts the binding of a given password to which
		security level. A value of 255 indicates an invalid
		binding."
	::= { snAgentGbl 39 }

snAgGblEnableSLB OBJECT-TYPE
	SYNTAX	INTEGER { disabled(0), enabled(1) }
	ACCESS	read-only
	STATUS	mandatory
	DESCRIPTION
		"Enable/disable Server Load Balancing."
	::= { snAgentGbl 40 }

snAgSoftwareFeature OBJECT-TYPE
    SYNTAX  OCTET STRING
	ACCESS	read-only
	STATUS	mandatory
	DESCRIPTION
		"A bit string representing the software feature of the running
		switch/router image. These features were conditional compiled
		to different product images. For each bit, exist feature has
		a value of 1, but non-exist feature has a value of 0.
		  octet 0, bit 0 - RMON
		  octet 0, bit 1 - ipx switching
		  octet 0, bit 2 - server load balancing
		  octet 0, bit 3 - layer 3 filter in switch
		  octet 0, bit 4 - ipx routing
		  octet 0, bit 5 - appletalk routing
		  octet 0, bit 6 - ip multicast routing
		  octet 0, bit 7 - local access control
		  octet 1, bit 0 - BGP routing
		  octet 1, bit 1 - loopback interface
		  octet 1, bit 2 - BigIron multi-management module
		  octet 1, bit 3 - BigIron SYSIF II
		  octet 1, bit 4 - BigIron POS support
		  octet 1, bit 5 - appletalk cable vlan
		  octet 1, bit 6 - 64 subnet
		  octet 1, bit 7 - multi-slot trunk
		  octet 2, bit 0 - TACACS
		  octet 2, bit 1 - Gigabit Ethernet port auto-negotiation mode
		  octet 2, bit 2 - FSRP
		  octet 2, bit 3 - Exodus requested OSPF enhancement
		  octet 2, bit 4 - OSPF NSSA
		  octet 2, bit 5 - POS
		  octet 2, bit 6 - QOS
		  octet 2, bit 7 - Single Span
		  octet 3, bit 0 - Fast Span
		  octet 3, bit 1 - Base L3
		  octet 3, bit 2 - static log buffer
		  octet 3, bit 3 - L2 POS
		  octet 3, bit 4 - BI15K
		  octet 3, bit 5 - L2 ATM
		  octet 3, bit 6 - ATM
		  octet 3, bit 7 - NETFLOW
		  octet 4, bit 0 - SFLOW
		  octet 4, bit 1 - GVRP
		  octet 4, bit 2 - GARP
		  octet 4, bit 3 - dynamic trunk
		  octet 4, bit 4 - IGC 8G
		  octet 4, bit 5 - rate limit
		  octet 4, bit 6 - IPC rate limit
		  octet 4, bit 7 - MPLS
		  octet 5, bit 0 - ISIS
		  octet 5, bit 1 - link aggregation
		  octet 5, bit 2 - port dual mode
		  octet 5, bit 3 - private vlan
		  octet 5, bit 4 - MBGP
		  octet 5, bit 5 - ipv6 protocol vlan
		  octet 5, bit 6 - X10G
		  octet 5, bit 7 - fastiron edge switch/router (gridiron)
		  octet 6, bit 0 - FDP
		  octet 6, bit 1 - port tag type
		  octet 6, bit 2 - wireless capable
		  octet 6, bit 3 - snSwPortVlanId object has changed from read-only to read-write
		Bit 0 is the least significant bit of an octet, and
		bit 7 is the most significant bit of an octet."
	::= { snAgentGbl 41 }

snAgGblEnableModuleInsertedTrap OBJECT-TYPE
	SYNTAX	INTEGER { disabled(0), enabled(1) }
	ACCESS	read-write
	STATUS	mandatory
	DESCRIPTION
		"Indicates whether the SNMP agent process is permitted to
		generate hardware module inserted to chassis traps."
    DEFVAL { enabled }
	::= { snAgentGbl 42 }

snAgGblEnableModuleRemovedTrap OBJECT-TYPE
	SYNTAX	INTEGER { disabled(0), enabled(1) }
	ACCESS	read-write
	STATUS	mandatory
	DESCRIPTION
		"Indicates whether the SNMP agent process is permitted to
		generate hardware module removed from chassis traps."
    DEFVAL { enabled }
	::= { snAgentGbl 43 }

snAgGblTrapMessage OBJECT-TYPE
    SYNTAX  DisplayString
	ACCESS	read-only
	STATUS	mandatory
	DESCRIPTION
		"A generic trap message string."
	::= { snAgentGbl 44 }

snAgGblEnableTelnetServer OBJECT-TYPE
	SYNTAX	INTEGER { disabled(0), enabled(1) }
	ACCESS	read-write
	STATUS	mandatory
	DESCRIPTION
		"Enable or disable telnet server in device."
    DEFVAL { enabled }
	::= { snAgentGbl 45 }

snAgGblTelnetPassword OBJECT-TYPE
	SYNTAX	DisplayString (SIZE (0..48))
	ACCESS	read-write
	STATUS	mandatory
	DESCRIPTION
		"Telnet Access Password and this is only 
		 allowed to use for setting but not for reading.
		 An SNMP-Get will get an zero string."
	::= { snAgentGbl 46 }

snAgBuildDate OBJECT-TYPE
	SYNTAX	DisplayString (SIZE(0..32))
	ACCESS	read-only
	STATUS	mandatory
	DESCRIPTION
		"The date of the built software."
	::= { snAgentGbl 47 }

snAgBuildtime OBJECT-TYPE
	SYNTAX	DisplayString (SIZE(0..32))
	ACCESS	read-only
	STATUS	mandatory
	DESCRIPTION
		"The time of the built software."
	::= { snAgentGbl 48 }

snAgBuildVer OBJECT-TYPE
	SYNTAX	DisplayString (SIZE(0..32))
	ACCESS	read-only
	STATUS	mandatory
	DESCRIPTION
		"The version of the built software in the form
		'major.minor.maintenance[letters]'."
	::= { snAgentGbl 49 }

snAgGblCpuUtil1SecAvg OBJECT-TYPE
	SYNTAX	Gauge
	ACCESS	read-only
	STATUS	mandatory
	DESCRIPTION
		"The statistics collection of 1 second CPU utilization."
	::= { snAgentGbl 50 }

snAgGblCpuUtil5SecAvg OBJECT-TYPE
	SYNTAX	Gauge
	ACCESS	read-only
	STATUS	mandatory
	DESCRIPTION
		"The statistics collection of 5 second CPU utilization."
	::= { snAgentGbl 51 }

snAgGblCpuUtil1MinAvg OBJECT-TYPE
	SYNTAX	Gauge
	ACCESS	read-only
	STATUS	mandatory
	DESCRIPTION
		"The statistics collection of 1 minute CPU utilization."
	::= { snAgentGbl 52 }

snAgGblDynMemUtil OBJECT-TYPE
	SYNTAX	Gauge
	ACCESS	read-only
	STATUS	mandatory
	DESCRIPTION
		"The system dynamic memory utilization, in unit of percentage."
	::= { snAgentGbl 53 }

snAgGblDynMemTotal OBJECT-TYPE
	SYNTAX	INTEGER
	ACCESS	read-only
	STATUS	mandatory
	DESCRIPTION
		"The total amount of system dynamic memory, in number of bytes."
	::= { snAgentGbl 54 }

snAgGblDynMemFree OBJECT-TYPE
	SYNTAX	INTEGER
	ACCESS	read-only
	STATUS	mandatory
	DESCRIPTION
		"The free amount of system dynamic memory, in number of bytes."
	::= { snAgentGbl 55 }

snAgImgLoadSPModuleType OBJECT-TYPE
	SYNTAX	INTEGER {
		other(1),
		vm1(2),
		pos12(3),
		pos48(4),
		atm(5),
		gignpa(6)
		}
	ACCESS	read-write
	STATUS	mandatory
	DESCRIPTION
		"The switch processor module type of which that receives
		the downloaded image."
	::= { snAgentGbl 56 }

snAgImgLoadSPModuleNumber OBJECT-TYPE
	SYNTAX	INTEGER
	ACCESS	read-write
	STATUS	mandatory
	DESCRIPTION
		"The slot numner of a switch processor module that receives
		the downloaded image. Setting value 0 applies to all SP
		modules."
	::= { snAgentGbl 57 }

snAgTrapHoldTime OBJECT-TYPE
	SYNTAX	INTEGER (1..600)
	ACCESS	read-write
	STATUS	mandatory
	DESCRIPTION
		"The time in seconds for which traps will be witheld
		during system initialization."
	::= { snAgentGbl 58 }

snAgSFlowSourceInterface OBJECT-TYPE
	SYNTAX   INTEGER
	ACCESS   read-write
	STATUS   mandatory
	DESCRIPTION
		"Use the ifIndex value here to specify the
		source interface to be used for sFlow packets.
		The interface should have IP address configured
		on it. Value of 0 indicates that source interface
		has not been configured for sFlow. Port 65534
		is used to specify a null port."
	::= { snAgentGbl 59 }

snAgGblTelnetLoginTimeout OBJECT-TYPE
	SYNTAX	INTEGER (1..10)
	ACCESS	read-write
	STATUS	mandatory
	DESCRIPTION
		"Telnet session login timeout value in minutes. Default is 1 minute."
	::= { snAgentGbl 60 }

snAgGblBannerExec OBJECT-TYPE
	SYNTAX	DisplayString
	ACCESS	read-write
	STATUS	mandatory
	DESCRIPTION
		"EXEC process creation banner. Insert newlines using '\n' within the string."
	::= { snAgentGbl 61 }

snAgGblBannerIncoming OBJECT-TYPE
	SYNTAX	DisplayString
	ACCESS	read-write
	STATUS	mandatory
	DESCRIPTION
		"Incoming terminal line banner. Insert newlines using '\n' within the string."
	::= { snAgentGbl 62 }

snAgGblBannerMotd OBJECT-TYPE
	SYNTAX	DisplayString
	ACCESS	read-write
	STATUS	mandatory
	DESCRIPTION
		"Message-of-the-day banner. Insert newlines using '\n' within the string."
	::= { snAgentGbl 63 }

snAgWebMgmtServerTcpPort OBJECT-TYPE
	SYNTAX	INTEGER (1..65535)
	ACCESS	read-write
	STATUS	mandatory
	DESCRIPTION
		"The TCP port number of web management interface."
	::= { snAgentGbl 64 }

-- Agent Board Table


snAgentBrdTable OBJECT-TYPE
	SYNTAX	SEQUENCE OF SnAgentBrdEntry
	ACCESS	not-accessible
	STATUS	mandatory
	DESCRIPTION
		"A table of each physical board information."
	::= { snAgentBrd 1 }

snAgentBrdEntry OBJECT-TYPE
	SYNTAX	SnAgentBrdEntry
	ACCESS	not-accessible
	STATUS	mandatory
	DESCRIPTION
		"A row in the Agent Board table."
	INDEX	{ snAgentBrdIndex }
	::= { snAgentBrdTable 1 }

SnAgentBrdEntry ::= SEQUENCE {
	snAgentBrdIndex
		INTEGER,
	snAgentBrdMainBrdDescription
		DisplayString,
	snAgentBrdMainBrdId
		OCTET STRING,
	snAgentBrdMainPortTotal
		INTEGER,
	snAgentBrdExpBrdDescription
		DisplayString,
	snAgentBrdExpBrdId
		OCTET STRING,
	snAgentBrdExpPortTotal
		INTEGER,
	snAgentBrdStatusLeds 
		INTEGER,
	snAgentBrdTrafficLeds 
		INTEGER,
	snAgentBrdMediaLeds 
		INTEGER,
	snAgentBrdSpeedLeds 
		INTEGER,
	snAgentBrdModuleStatus
		INTEGER,
	snAgentBrdRedundantStatus
		INTEGER,
	snAgentBrdAlarmLeds 
		INTEGER,
	snAgentBrdTxTrafficLeds 
		INTEGER,
	snAgentBrdRxTrafficLeds 
		INTEGER,
	snAgentBrdStatusLedString
		OCTET STRING,
	snAgentBrdTrafficLedString
		OCTET STRING,
	snAgentBrdMediaLedString
		OCTET STRING,
	snAgentBrdSpeedLedString
		OCTET STRING,
	snAgentBrdAlarmLedString
		OCTET STRING,
	snAgentBrdTxTrafficLedString
		OCTET STRING,
	snAgentBrdRxTrafficLedString
		OCTET STRING
	}

snAgentBrdIndex OBJECT-TYPE
	SYNTAX	INTEGER (1..15)
	ACCESS	read-only
	STATUS	mandatory
	DESCRIPTION
		"The index to the Agent Interface Table."
	::= { snAgentBrdEntry 1 }

snAgentBrdMainBrdDescription OBJECT-TYPE
    SYNTAX DisplayString (SIZE(0..128))
    ACCESS read-only
    STATUS mandatory
    DESCRIPTION
        "The main board description string."
    ::= { snAgentBrdEntry 2 }

snAgentBrdMainBrdId OBJECT-TYPE
    SYNTAX OCTET STRING
    ACCESS read-only
    STATUS mandatory
    DESCRIPTION
        "The main board identifier, which can uniquely identify a board
        type. It is an encoded octet string with the following meaning:
          octet 0  - octet string format version, which identifies the
                     format of this string.
        If format version octet has the value 2, the octets after the
        version octet have the following meaning:
          octet 1  - product type: 
						BI_WG					0x57
						BI_BB					0x42
						BI_NI					0x4E
						BI_NI2					0x32
						NI_M4					0x4D
						BI_SLB					0x53
          octet 2  - module type:
						MASTER_FIBER_8G			0x0
						MASTER_FIBER_4G			0x1
						MASTER_COPPER_16		0x2
						SLAVE_FIBER_4G			0x3
						FI_MASTER_FIBER_2G		0x4
						FI_MASTER_FIBER_4G		0x5
						MASTER_COPPER_8G		0x6
						FI_MASTER_FIBER_8G		0x7
						SLAVE_FIBER_8G			0x8
						MASTER_COPPER_12_2		0x9
						SLAVE_COPPER_24			0xA
						FI_SLAVE_COPPER_24		0xB
						SLAVE_100FX_8			0xD
						SLAVE_100FX_16			0xC
						SLAVE_COPPER_8G			0xE
						SLAVE_COPPER_16_2		0xF
						STACK_FIBER_8G			0x10
						STACK_COPPER_8G			0x11
						MASTER_FIBER_2G			0x12	
						SLAVE_100FX_24			0x13
						MASTER_FIBER_0G			0x14	
						POS_622M				0x15
						POS_155M				0x16
						SLAVE_FIBER_2G			0x17
						SLAVE_COPPER_2G			0x18
						FI_SLAVE_FIBER_2G		0x19
						FI_SLAVE_FIBER_4G		0x1A
						FI_SLAVE_FIBER_8G		0x1B
						FI_SLAVE_COPPER_8G		0x1C
						FI_MASTER_COPPER_8G		0x1D
						POS_155M2P				0x1E
						FI_MASTER_COPPER_4G		0x1F
						FI_MASTER_COPPER_2G		0x20
						MASTER_COPPER_4G		0x21
						MASTER_COPPER_2G		0x22
						MASTER_M4_8G			0x23
						MASTER_M4_4G			0x24
						MASTER_M4_2G			0x25
						MASTER_M4_0G			0x26	
						MASTER_M5_0G			0x27	
						POS_2488M				0x28	
						SLAVE_M5_0G				0x29	
						POS_N2488M				0x2A	
						STACK_IPC_48_2			0x2B	
						SLAVE_NPA_FIBER_4G		0x2C	
						ATM_2PORT				0x2D	
						ATM_4PORT				0x2E	
						SLAVE_FIBER_10G			0x2F
						STACK_FES_48_2			0x30
						STACK_FES_24_2			0x31
						STACK_FES_96_4			0x32
						STACK_FES_12G			0x33
						STACK_FESX_24G			0x34
						STACK_FESX_24_2_G		0x35
						STACK_FESX_24_1_G		0x36
						STACK_FESX_48G			0x37
						STACK_FESX_48_2_G		0x38
						STACK_FESX_48_1_G		0x39
						SUPERX_FI_MGMT		    0x40
						SUPERX_FI_2P10G 		0x41
						SUPERX_FI_24GC  		0x42
						SUPERX_FI_24GF  		0x43
						SUPERX_FI_2P10G_WAN 	0x44
						SUPERX_FI_MGMT_II       0x4a
						SLAVE_JC_48E			0xC3	
						SLAVE_JC_48T			0xC4	
						MASTER_JC_M4_8G			0xC5	
						SLAVE_JC_8G				0xC6	
						SLAVE_JC_B16GF			0xC8	
						MASTER_JC_B2404			0xC9	
						SLAVE_JC_B16GC			0xCA	
          octet 3  - processor type, PVR_M603=3, PVR_M604=4, PVR_M603E=6,
                     PVR_M603EV=7, PVR_M750=8, PVR_M604E=9, PVR_M8245=81
          octet 4 to
          octet 5  - processor speed in MHz
          octet 6  - MAC type:
          				MAC_NONE=0
          				MAC_SEEQ_10_100=1, 
          				MAC_DEC_10_100=2,
          				MAC_3COM_10_100=3,
						MAC_X10GMAC_10000=4,
                     	MAC_SEEQ_1000=5, 
						MAC_GMAC_1000=6,
						MAC_VLSI_1000=7
          octet 7  - PHY type, PHY_NONE=0, PHY_QSI=1, PHY_BROADCOM=2,
                     PHY_ICS=3, PHY_NATIONAL=4, PHY_LEVEL1=6,
                     PHY_BROADCOM_10_100=7, PHY_LEVEL24=8,
                     PHY_BROADCOM_10000=9 (for 10G),
                     PHY_3COM_10_100=9 (for others)
          octet 8  - port type, COPPER=0, FIBER=1
          octet 9  - fiber port type, NONFIBER=0, SX_FIBER=1,
                     LX_FIBER=2, LHX_FIBER=3, LX_SX_FIBER=4,
                     LHB_FIBER=5
          octet 10 to
          octet 13 - DRAM size in KBytes
          octet 14 to
          octet 17 - boot flash size in KBytes
          octet 18 to
          octet 21 - code flash size in KBytes
          octet 22 to
          octet 27 - serial number.
          octet 28 - chassis backplane type. 
		 	chassis4000	= 	0x00
		 	chassis8000	=	0x02
		 	chassis15000	=	0x01
		 	chassisFISX	=	0x04
		 	Turbo8		=	0x07 (stack2)
		 	FastIron2	=	0x06 (stack1)"
	::= { snAgentBrdEntry 3 }


snAgentBrdMainPortTotal OBJECT-TYPE
    SYNTAX INTEGER (1..100)
    ACCESS read-only
    STATUS mandatory
    DESCRIPTION
        "The total number of ports for the main board."
    ::= { snAgentBrdEntry 4 }


snAgentBrdExpBrdDescription OBJECT-TYPE
    SYNTAX DisplayString (SIZE(0..128))
    ACCESS read-only
    STATUS mandatory
    DESCRIPTION
        "The expansion board description string. Expansion
        board are those boards attaching on the main board."
    ::= { snAgentBrdEntry 5 }


snAgentBrdExpBrdId OBJECT-TYPE
    SYNTAX OCTET STRING
    ACCESS read-only
    STATUS mandatory
    DESCRIPTION
        "The expansion board identifier. Expansion board are those
        boards attaching on the main board. It is an encoded octet
		string with the following meaning:
          octet 0  - octet string format version, which identifies
                     the format of this string.
        If format version octet has the value 1, the octets after
        the version octet have the following meaning:
          octet 1  - expansion board type, HUNDRED_MEG_1PORT=1,
                     HUNDRED_MEG_2PORT=2, HUNDRED_MEG_1PORT_COPPER=3,
                     HUNDRED_MEG_2PORT_COPPER=4, HUNDRED_MEG_2PORT_LX=5,
                     GIGA_1PORT=8, GIGA_2PORT=9
          octet 2  - fiber port type, NONFIBER=0, SX_FIBER=1,
                     LX_FIBER=2, LHX_FIBER=3, LX_SX_FIBER=4, LHB_FIBER=5"
    ::= { snAgentBrdEntry 6 }


snAgentBrdExpPortTotal OBJECT-TYPE
	SYNTAX INTEGER (0..24)
    ACCESS read-only
    STATUS mandatory
    DESCRIPTION
        "The total number of ports for the expansion board."
    ::= { snAgentBrdEntry 7 }


snAgentBrdStatusLeds OBJECT-TYPE
	SYNTAX	INTEGER
	ACCESS	read-only
	STATUS  deprecated
	DESCRIPTION
		"A bit array that contains the value of the
		front panel status LEDs. This is a bit-map; 
		each LED is encoded into 1 bit for each switch
		port.  The maximum number of ports in one chassis 
		is 32 that means 32 Ports Status LEDs. The expansion port 
		number always begins from the last main port number.  
		The following shows the meaning of each bit for each 
		switch port:

		  bit value  meaning
		  --------   ---------  
		     0         off (Link off)
			 1         on  (Link on)

		The bitmap of LEDs are as following: 
			  
                 (Port1)            (Port4)                    (Port8)
        Bit      (Bit0)             (Bit3)                      (Bit7)
		Byte 1:	 LED1	LED2   LED3  LED4   LED5   LED6   LED7   LED8    
		Byte 2:	 LED9	LED10  LED11 LED12  LED13  LED14  LED15  LED16     
		Byte 3:	 LED17	LED18  LED19 LED20  LED21  LED22  LED23  LED24
		(It was obsoleted after release 07100, replaced by snAgentBrdStatusLedString)"
	::= { snAgentBrdEntry 8 }


snAgentBrdTrafficLeds OBJECT-TYPE
	SYNTAX	INTEGER
	ACCESS	read-only
	STATUS  deprecated
	DESCRIPTION
		"A bit array that contains the value of the
		front panel traffic LEDs. This is a packed bit string; 
		each LED is encoded into 1 bit for each switch
		port.  The maximum number of ports in one chassis 
		is 24 that means 24 Ports Traffic LEDs. The expansion port 
		number always begins from the last main port number.  
		The following shows the meaning of each bit for each 
		switch port:

		  bit value  meaning
		  --------   ---------  
		     0         off (no traffic)
			 1         on  (traffic)

		The bitmap of LEDs are as following: 
			  
                 (Port1)            (Port4)                    (Port8)
        Bit      (Bit0)             (Bit3)                      (Bit7)
		Byte 1:	 LED1	LED2   LED3  LED4   LED5   LED6   LED7   LED8    
		Byte 2:	 LED9	LED10  LED11 LED12  LED13  LED14  LED15  LED16     
		Byte 3:	 LED17	LED18  LED19 LED20  LED21  LED22  LED23  LED24
		(It was obsoleted after release 07100, replaced by snAgentBrdTrafficLedString)"
	::= { snAgentBrdEntry 9 }


snAgentBrdMediaLeds OBJECT-TYPE
	SYNTAX	INTEGER
	ACCESS	read-only
	STATUS  deprecated
	DESCRIPTION
		"A bit array that contains the value of the
		front panel media LEDs. This is a packed bit string; 
		each LED is encoded into 1 bit for each switch port.  
		The maximum number of ports in one chassis is 24 
		that means 24 Ports Media LEDs.  The expansion port 
		number always begins from the last main port number. 
		The following shows the meaning of each bit for each 
		switch port:

		bit value  meaning   
		---------  -------
      	  0        half duplex
      	  1        full duplex

		The bitmap of LEDs are as following: 
		         (Port1)            (Port4)                    (Port8)
        Bit      (Bit0)             (Bit3)                      (Bit7)
		Byte 1:	 LED1	LED2   LED3  LED4   LED5   LED6   LED7   LED8    
		Byte 2:	 LED9	LED10  LED11 LED12  LED13  LED14  LED15  LED16     
		Byte 3:	 LED17	LED18  LED19 LED20  LED21  LED22  LED23  LED24			  
		(It was obsoleted after release 07100, replaced by snAgentBrdMediaLedString)"
	::= { snAgentBrdEntry 10 }



snAgentBrdSpeedLeds OBJECT-TYPE
	SYNTAX	INTEGER
	ACCESS	read-only
	STATUS  deprecated
	DESCRIPTION
		"A bit array that contains the value of the
		front panel media LEDs. This is a packed bit string; 
		each LED is encoded into 1 bit for each switch port.  
		The maximum number of ports in one chassis is 24 
		that means 24 Ports Speed LEDs.  The expansion port 
		number always begins from the last main port number. 
		The following shows the meaning of each bit for each 
		switch port:

		bit value  meaning   
		---------  -------
      	  0        10 MBit
      	  1        100 MBit

		The bitmap of LEDs are as following: 
		         (Port1)            (Port4)                    (Port8)
        Bit      (Bit0)             (Bit3)                      (Bit7)
		Byte 1:	 LED1	LED2   LED3  LED4   LED5   LED6   LED7   LED8    
		Byte 2:	 LED9	LED10  LED11 LED12  LED13  LED14  LED15  LED16     
		Byte 3:	 LED17	LED18  LED19 LED20  LED21  LED22  LED23  LED24			  
		(It was obsoleted after release 07100, replaced by snAgentBrdSpeedLedString)"
	::= { snAgentBrdEntry 11 }

snAgentBrdModuleStatus OBJECT-TYPE
	SYNTAX  INTEGER {
		moduleEmpty(0),             
		moduleGoingDown(2),
		moduleRejected(3),
		moduleBad(4),
		moduleComingUp(9),
		moduleRunning(10)
		}
	ACCESS  read-only
	STATUS  mandatory
	DESCRIPTION
		"By default, this mode is set to notActivated(0).
		moduleEmpty(0) ......... The slot of the chassis is empty.
		moduleGoingDown(2) ..... The module is going down.
		moduleRejected(3) ...... The module is being rejected due to wrong configuration.
		moduleBad(4) ........... The module Hardware is bad.
		moduleComingUp(9) ...... The module is in power-up cycle.
		moduleRunning(10) ....... The module is running."
	::= { snAgentBrdEntry 12 }

snAgentBrdRedundantStatus OBJECT-TYPE
	SYNTAX  INTEGER {
		other(1),
		active(2),             
		standby(3),
		crashed(4),
		comingUp(5)
		}
	ACCESS  read-only
	STATUS  mandatory
	DESCRIPTION
		"The redundant status of a module. Non-management module always
		returns other(1). Management module returns the rest of the
		states."
	::= { snAgentBrdEntry 13 }

snAgentBrdAlarmLeds OBJECT-TYPE
	SYNTAX	INTEGER
	ACCESS	read-only
	STATUS  deprecated
	DESCRIPTION
		"A bit array that contains the value of the
		front panel media LEDs (for POS Module Only). This is a packed bit string; 
		each LED is encoded into 1 bit for each switch port.  
		The maximum number of ports in one chassis is 24 
		that means 24 Ports Speed LEDs.  The expansion port 
		number always begins from the last main port number. 
		The following shows the meaning of each bit for each 
		switch port:

		bit value  meaning   
		---------  -------
      	  0        no alarm
      	  1        alarm

		The bitmap of LEDs are as following: 
		         (Port1)            (Port4)                    (Port8)
        Bit      (Bit0)             (Bit3)                      (Bit7)
		Byte 1:	 LED1	LED2   LED3  LED4   LED5   LED6   LED7   LED8    
		Byte 2:	 LED9	LED10  LED11 LED12  LED13  LED14  LED15  LED16     
		Byte 3:	 LED17	LED18  LED19 LED20  LED21  LED22  LED23  LED24			  
		(It was obsoleted after release 07100, replaced by snAgentBrdAlarmLedString)"
	::= { snAgentBrdEntry 14 }


snAgentBrdTxTrafficLeds OBJECT-TYPE
	SYNTAX	INTEGER
	ACCESS	read-only
	STATUS  deprecated
	DESCRIPTION
		"A bit array that contains the value of the
		front panel transmit traffic LEDs (for POS Module Only). This is a packed bit string; 
		each LED is encoded into 1 bit for each switch
		port.  The maximum number of ports in one chassis 
		is 24 that means 24 Ports Transmit Traffic LEDs. The expansion port 
		number always begins from the last main port number.  
		The following shows the meaning of each bit for each 
		switch port:

		  bit value  meaning
		  --------   ---------  
		     0         off (no transmit traffic)
			 1         on  (transmit traffic)

		The bitmap of LEDs are as following: 
			  
                 (Port1)            (Port4)                    (Port8)
        Bit      (Bit0)             (Bit3)                      (Bit7)
		Byte 1:	 LED1	LED2   LED3  LED4   LED5   LED6   LED7   LED8    
		Byte 2:	 LED9	LED10  LED11 LED12  LED13  LED14  LED15  LED16     
		Byte 3:	 LED17	LED18  LED19 LED20  LED21  LED22  LED23  LED24
		(It was obsoleted after release 07100, replaced by snAgentBrdTxTrafficLedString)"
	::= { snAgentBrdEntry 15 }

snAgentBrdRxTrafficLeds OBJECT-TYPE
	SYNTAX	INTEGER
	ACCESS	read-only
	STATUS  deprecated
	DESCRIPTION
		"A bit array that contains the value of the
		front panel receive traffic LEDs (for POS Module Only). This is a packed bit string; 
		each LED is encoded into 1 bit for each switch
		port.  The maximum number of ports in one chassis 
		is 24 that means 24 Ports Receive Traffic LEDs. The expansion port 
		number always begins from the last main port number.  
		The following shows the meaning of each bit for each 
		switch port:

		  bit value  meaning
		  --------   ---------  
		     0         off (no receive traffic)
			 1         on  (receive traffic)

		The bitmap of LEDs are as following: 
			  
                 (Port1)            (Port4)                    (Port8)
        Bit      (Bit0)             (Bit3)                      (Bit7)
		Byte 1:	 LED1	LED2   LED3  LED4   LED5   LED6   LED7   LED8    
		Byte 2:	 LED9	LED10  LED11 LED12  LED13  LED14  LED15  LED16     
		Byte 3:	 LED17	LED18  LED19 LED20  LED21  LED22  LED23  LED24
		(It was obsoleted after release 07100, replaced by snAgentBrdRxTrafficLedString)"
	::= { snAgentBrdEntry 16 }

snAgentBrdStatusLedString OBJECT-TYPE
	SYNTAX	OCTET STRING
	ACCESS	read-only
	STATUS	mandatory
	DESCRIPTION
		"A bit array that contains the value of the
		front panel status LEDs. This is a bit-map; 
		each LED is encoded into 1 bit for each switch
		port. The following shows the meaning of each
		bit for each switch port:

		  bit value  meaning
		  --------   ---------  
		     0         off (Link off)
			 1         on  (Link on)

		The bitmap of LEDs are as following: 
			  
                 (Port1)            (Port4)                    (Port8)
        Bit      (Bit0)             (Bit3)                      (Bit7)
		Byte 1:	 LED1	LED2   LED3  LED4   LED5   LED6   LED7   LED8    
		Byte 2:	 LED9	LED10  LED11 LED12  LED13  LED14  LED15  LED16     
		Byte 3:	 LED17	LED18  LED19 LED20  LED21  LED22  LED23  LED24
        --------"
	::= { snAgentBrdEntry 17 }

snAgentBrdTrafficLedString OBJECT-TYPE
	SYNTAX	OCTET STRING
	ACCESS	read-only
	STATUS	mandatory
	DESCRIPTION
		"A bit array that contains the value of the
		front panel traffic LEDs. This is a packed bit string; 
		each LED is encoded into 1 bit for each switch
		port. The following shows the meaning of each
		bit for each switch port:

		  bit value  meaning
		  --------   ---------  
		     0         off (no traffic)
			 1         on  (traffic)

		The bitmap of LEDs are as following: 
			  
                 (Port1)            (Port4)                    (Port8)
        Bit      (Bit0)             (Bit3)                      (Bit7)
		Byte 1:	 LED1	LED2   LED3  LED4   LED5   LED6   LED7   LED8    
		Byte 2:	 LED9	LED10  LED11 LED12  LED13  LED14  LED15  LED16     
		Byte 3:	 LED17	LED18  LED19 LED20  LED21  LED22  LED23  LED24
        --------"
	::= { snAgentBrdEntry 18 }

snAgentBrdMediaLedString OBJECT-TYPE
	SYNTAX	OCTET STRING
	ACCESS	read-only
	STATUS	mandatory
	DESCRIPTION
		"A bit array that contains the value of the
		front panel media LEDs. This is a packed bit string;
		each LED is encoded into 1 bit for each switch port.
		The following shows the meaning of each bit for each
		switch port:

		bit value  meaning   
		---------  -------
      	  0        half duplex
      	  1        full duplex

		The bitmap of LEDs are as following: 
		         (Port1)            (Port4)                    (Port8)
        Bit      (Bit0)             (Bit3)                      (Bit7)
		Byte 1:	 LED1	LED2   LED3  LED4   LED5   LED6   LED7   LED8    
		Byte 2:	 LED9	LED10  LED11 LED12  LED13  LED14  LED15  LED16     
		Byte 3:	 LED17	LED18  LED19 LED20  LED21  LED22  LED23  LED24			  
        ---------"
	::= { snAgentBrdEntry 19 }

snAgentBrdSpeedLedString OBJECT-TYPE
	SYNTAX	OCTET STRING
	ACCESS	read-only
	STATUS	mandatory
	DESCRIPTION
		"A bit array that contains the value of the
		front panel media LEDs. This is a packed bit string;
		each LED is encoded into 1 bit for each switch port.
		The following shows the meaning of each bit for each
		switch port:

		bit value  meaning   
		---------  -------
      	  0        10 MBit
      	  1        100 MBit

		The bitmap of LEDs are as following: 
		         (Port1)            (Port4)                    (Port8)
        Bit      (Bit0)             (Bit3)                      (Bit7)
		Byte 1:	 LED1	LED2   LED3  LED4   LED5   LED6   LED7   LED8    
		Byte 2:	 LED9	LED10  LED11 LED12  LED13  LED14  LED15  LED16     
		Byte 3:	 LED17	LED18  LED19 LED20  LED21  LED22  LED23  LED24			  
        ---------"
	::= { snAgentBrdEntry 20 }

snAgentBrdAlarmLedString OBJECT-TYPE
	SYNTAX	OCTET STRING
	ACCESS	read-only
	STATUS	mandatory
	DESCRIPTION
		"A bit array that contains the value of the
		front panel media LEDs (for POS Module Only).
		This is a packed bit string; each LED is encoded
		into 1 bit for each switch port. The following
		shows the meaning of each bit for each switch port:

		bit value  meaning   
		---------  -------
      	  0        no alarm
      	  1        alarm

		The bitmap of LEDs are as following: 
		         (Port1)            (Port4)                    (Port8)
        Bit      (Bit0)             (Bit3)                      (Bit7)
		Byte 1:	 LED1	LED2   LED3  LED4   LED5   LED6   LED7   LED8    
		Byte 2:	 LED9	LED10  LED11 LED12  LED13  LED14  LED15  LED16     
		Byte 3:	 LED17	LED18  LED19 LED20  LED21  LED22  LED23  LED24			  
        ---------"
	::= { snAgentBrdEntry 21 }

snAgentBrdTxTrafficLedString OBJECT-TYPE
	SYNTAX	OCTET STRING
	ACCESS	read-only
	STATUS	mandatory
	DESCRIPTION
		"A bit array that contains the value of the
		front panel transmit traffic LEDs (for POS Module Only).
		This is a packed bit string; each LED is encoded into
		1 bit for each switch port. The following shows the
		meaning of each bit for each switch port:

		  bit value  meaning
		  --------   ---------  
		     0         off (no transmit traffic)
			 1         on  (transmit traffic)

		The bitmap of LEDs are as following: 
			  
                 (Port1)            (Port4)                    (Port8)
        Bit      (Bit0)             (Bit3)                      (Bit7)
		Byte 1:	 LED1	LED2   LED3  LED4   LED5   LED6   LED7   LED8    
		Byte 2:	 LED9	LED10  LED11 LED12  LED13  LED14  LED15  LED16     
		Byte 3:	 LED17	LED18  LED19 LED20  LED21  LED22  LED23  LED24
        --------"
	::= { snAgentBrdEntry 22 }

snAgentBrdRxTrafficLedString OBJECT-TYPE
	SYNTAX	OCTET STRING
	ACCESS	read-only
	STATUS	mandatory
	DESCRIPTION
		"A bit array that contains the value of the
		front panel receive traffic LEDs (for POS Module Only).
		This is a packed bit string; each LED is encoded into
		1 bit for each switch port. The following shows the
		meaning of each bit for each switch port:

		  bit value  meaning
		  --------   ---------  
		     0         off (no receive traffic)
			 1         on  (receive traffic)

		The bitmap of LEDs are as following: 
			  
                 (Port1)            (Port4)                    (Port8)
        Bit      (Bit0)             (Bit3)                      (Bit7)
		Byte 1:	 LED1	LED2   LED3  LED4   LED5   LED6   LED7   LED8    
		Byte 2:	 LED9	LED10  LED11 LED12  LED13  LED14  LED15  LED16     
		Byte 3:	 LED17	LED18  LED19 LED20  LED21  LED22  LED23  LED24
        --------"
	::= { snAgentBrdEntry 23 }

-- Trap Receiver Table


snAgTrpRcvrTable OBJECT-TYPE
	SYNTAX	SEQUENCE OF SnAgTrpRcvrEntry
	ACCESS	not-accessible
	STATUS	mandatory
	DESCRIPTION
		"A table of managers which to send traps."
	::= { snAgentTrp 1 }

snAgTrpRcvrEntry OBJECT-TYPE
	SYNTAX	SnAgTrpRcvrEntry
	ACCESS	not-accessible
	STATUS	mandatory
	DESCRIPTION
		"A row in the trap receiver table.
		The column snAgTrpRcvrStatus is used to create
		and delete rows in the table. Creation requires
		a SET PDU with objects snAgTrpRcvrIndex,
		snAgTrpRcvrIpAddr, snAgTrpRcvrComm and 
		snAgTrpRcvrStatus."
	INDEX	{ snAgTrpRcvrIndex }
	::= { snAgTrpRcvrTable 1 }

SnAgTrpRcvrEntry ::= SEQUENCE {
	snAgTrpRcvrIndex
		INTEGER,
	snAgTrpRcvrIpAddr
		IpAddress,
	snAgTrpRcvrComm
		OCTET STRING,
	snAgTrpRcvrStatus
		INTEGER,
	snAgTrpRcvrUDPPort
		INTEGER
	}

snAgTrpRcvrIndex OBJECT-TYPE
	SYNTAX	INTEGER (1..10)
	ACCESS	read-only
	STATUS	mandatory
	DESCRIPTION
		"The index to the Trap Receiver Table."
	::= { snAgTrpRcvrEntry 1 }

snAgTrpRcvrIpAddr OBJECT-TYPE
	SYNTAX	IpAddress
	ACCESS	read-write
	STATUS	mandatory
	DESCRIPTION
		"The ip address for
		SNMP manager that is to receive the trap."
	::= { snAgTrpRcvrEntry 2 }

snAgTrpRcvrComm OBJECT-TYPE
	SYNTAX	OCTET STRING (SIZE(0..32))
	ACCESS	read-write
	STATUS	mandatory
	DESCRIPTION
		"Community string to use."
	::= { snAgTrpRcvrEntry 3 }


snAgTrpRcvrStatus OBJECT-TYPE
	SYNTAX	INTEGER {
		other(1),
		valid(2),
		delete(3),
		create(4),
		ignore(5)
		}
	ACCESS	read-write
	STATUS	mandatory
	DESCRIPTION
		"This object is used to create and
		delete rows in the table and control
		if they are used. The values
		that can be written are:
		  ignore(5)...don't use this entry to
		                send traps to at this time
		  delete(3)...deletes the row
		  create(4)...creates a new row

		If the row exists, then a SET with
		value of create(5) returns error
		'badValue'. Deleted rows go away
		immediately. The following values
		can be returned on reads:
		  other(1)....some other case
		  valid(2)....the row exists and is valid
		  ignore(5)...don't use this entry to
		                send traps to at this time"
	::= { snAgTrpRcvrEntry 4 }

snAgTrpRcvrUDPPort       OBJECT-TYPE
	SYNTAX	INTEGER	 (0..65535)
	ACCESS  read-write
	STATUS  mandatory
	DESCRIPTION
		"UDP port number of the trap receiver."
    DEFVAL { 162 }
	::= { snAgTrpRcvrEntry 5 }


-- Boot Sequence Table


snAgBootSeqTable OBJECT-TYPE
	SYNTAX	SEQUENCE OF SnAgBootSeqEntry
	ACCESS	not-accessible
	STATUS	mandatory
	DESCRIPTION
		"A table of image load sequnce instructions to the boot code.
		Boot code will start from instruction of the first valid entry
		to load the image. If failed, it will use the second valid
		entry and so on, until a succesful load has completed. Each
		entry must have an unique instruction, duplicate instructions
		will be rejected."
	::= { snAgentBoot 1 }

snAgBootSeqEntry OBJECT-TYPE
	SYNTAX	SnAgBootSeqEntry
	ACCESS	not-accessible
	STATUS	mandatory
	DESCRIPTION
		"A row in the boot sequence table."
	INDEX	{ snAgBootSeqIndex }
	::= { snAgBootSeqTable 1 }

SnAgBootSeqEntry ::= SEQUENCE {
	snAgBootSeqIndex
		INTEGER,
	snAgBootSeqInstruction
		INTEGER,
	snAgBootSeqIpAddr
		IpAddress,
	snAgBootSeqFilename
		DisplayString,
	snAgBootSeqRowStatus
		INTEGER
	}

snAgBootSeqIndex OBJECT-TYPE
	SYNTAX	INTEGER (1..4)
	ACCESS	read-only
	STATUS	mandatory
	DESCRIPTION
		"The index to the boot sequence table."
	::= { snAgBootSeqEntry 1 }

snAgBootSeqInstruction OBJECT-TYPE
	SYNTAX	INTEGER {
		fromPrimaryFlash(1),
		fromSecondaryFlash(2),
		fromTftpServer(3),
		fromBootpServer(4) }
	ACCESS	read-write
	STATUS	mandatory
	DESCRIPTION
		"The instruction for the boot code."
	::= { snAgBootSeqEntry 2 }

snAgBootSeqIpAddr OBJECT-TYPE
	SYNTAX	IpAddress
	ACCESS	read-write
	STATUS	mandatory
	DESCRIPTION
		"The ip address of the TFTP server if snAgBootSeqInstruction
		was set to 'fromTftpServer'; otherwise, this object is not
		used in any other boot instruction."
	::= { snAgBootSeqEntry 3 }

snAgBootSeqFilename OBJECT-TYPE
	SYNTAX	DisplayString (SIZE (0..32))
	ACCESS	read-write
	STATUS	mandatory
	DESCRIPTION
		"The image filename on the TFTP server if snAgBootSeqInstruction
		was set to 'fromTftpServer'; otherwise, this object is not
		used in any other boot instruction."
	::= { snAgBootSeqEntry 4 }

snAgBootSeqRowStatus OBJECT-TYPE
	SYNTAX	INTEGER	{
		other(1),
		valid(2),
		delete(3),
		create(4) }
	ACCESS	read-write
	STATUS	mandatory
	DESCRIPTION
		"To create or delete a boot sequence table entry."
	::= { snAgBootSeqEntry 5 }

--- Encoded Octet Strings for the Configuration File Transfer


snAgCfgEosTable OBJECT-TYPE
	SYNTAX	SEQUENCE OF SnAgCfgEosEntry
	ACCESS	not-accessible
	STATUS	mandatory
	DESCRIPTION
		"This table represents the fragmented Configuration File data packet 
		with checksum include in each rows of this table.  A SNMP-SET
		represents configuration file download, and a SNMP-GET represents
		configuration file upload.  This action is only if the SNMP-SET of
		snAgCfgLoad command is sent along with this table consecutively.  The 
		applicable snAgCfgLoad command value is as followings:
		uploadFromFlashToNMS(23),
		downloadToFlashFromNMS(24),
		uploadFromDramToNMS(25),
		downloadToDramFromNMS(26)." 
	::= { snAgCfgEos 1 }


snAgCfgEosEntry OBJECT-TYPE
	SYNTAX	SnAgCfgEosEntry	
	ACCESS	not-accessible
	STATUS	mandatory
	DESCRIPTION
		"An EOS row in the table of encoded octet strings for table 
		snAgCfgEosTable. "
	INDEX  { snAgCfgEosIndex }
	::= { snAgCfgEosTable 1 }



SnAgCfgEosEntry ::= 
	SEQUENCE {
	snAgCfgEosIndex
		INTEGER,
	snAgCfgEosPacket 
		OCTET STRING,
	snAgCfgEosChkSum
		INTEGER
	}


snAgCfgEosIndex OBJECT-TYPE
	SYNTAX  INTEGER 
	ACCESS  read-only
	STATUS  mandatory
	DESCRIPTION
		 "Each VLAN EOS Buffer Identifier have a multiple 
		 VLAN table entries."
	::= { snAgCfgEosEntry 1 }

snAgCfgEosPacket OBJECT-TYPE
	SYNTAX	OCTET STRING (SIZE(0..1000))
	ACCESS	read-write
	STATUS	mandatory
	DESCRIPTION
		"An encoded octet string. On reads it contains an integral 
		number of configuration file data packets. The size 
		of each encoded octet string is less than or equal to 1400
		bytes."
	::= { snAgCfgEosEntry 2 }


snAgCfgEosChkSum OBJECT-TYPE
	SYNTAX  INTEGER 
	ACCESS  read-write
	STATUS  mandatory
	DESCRIPTION
		 "A checksum of each configuration file data packet." 
	::= { snAgCfgEosEntry 3 }


-- Stackable Management Group

snStackGen				OBJECT IDENTIFIER ::= { snStack 1 }
snStackSecSwitchInfo	OBJECT IDENTIFIER ::= { snStack 2 }

-- MIB Objects


-- General Stackable Management Information

snStackPriSwitchMode OBJECT-TYPE
	SYNTAX  INTEGER {
		disabled(0),             
		enabled(1)
		}
	ACCESS  read-write
	STATUS  mandatory
	DESCRIPTION
		"The Stackable Management Primary Switch mode
		 either enabled or disabled and the default is 
		 disabled mode.
		 enabled(1)...........primary switch enabled
		 disabled(0)..........primary switch disabled"  
	::= { snStackGen 1 }

snStackMaxSecSwitch OBJECT-TYPE
	SYNTAX  INTEGER 
	ACCESS  read-only
	STATUS  mandatory
	DESCRIPTION
		"The Maximum Secondary Switches are allowed in the
		 Stackable Management Group."
	::= { snStackGen 2 }

snStackTotalSecSwitch OBJECT-TYPE
	SYNTAX  INTEGER 
	ACCESS  read-only
	STATUS  mandatory
	DESCRIPTION
		"The Total Secondary Switches currently connected to the
		 Stackable Management Group."
	::= { snStackGen 3 }

snStackSyncAllSecSwitch OBJECT-TYPE
	SYNTAX  INTEGER {
		normal(0),
		invalid(1),
		device(2),
		global(3),
		local(4)
		}
	ACCESS  read-write
	STATUS  mandatory
	DESCRIPTION
		"Synchronize all the secondary switches in the
		 Stackable Management Group with the following commands.
		 device(2)...........device related parameters.
		 global(3)...........global parameters.  
		 local(4)............local parameters.
		 The return result of the above commands are either
		 normal(0)...........normal condition.
		 invalid(1)...........invalid result."  
	::= { snStackGen 4 }

snStackSmSlotIndex OBJECT-TYPE
	SYNTAX	INTEGER (0..8)
	ACCESS	read-write
	STATUS	mandatory
	DESCRIPTION
		"The Slot 0 is the Master slot and Slot 1-8 are slaves. 
		 All the slot-based MIB data can be retrieved with respect to 
		 this slot index such as snChassis global MIB. "
	::= { snStackGen 5 }

snStackFmpSetProcess OBJECT-TYPE
	SYNTAX	INTEGER { 
						normal(0), 
						pending(1), 
						failure(2)
					}
	ACCESS	read-only
	STATUS	mandatory
	DESCRIPTION
		"normal(0)  - The set process is either in an idle state or FMP-SET-SUCCESS state.
		 pending(1) - The pending process is waiting for the result of an FMP-SET.
		 failure(2) - The failure result of an FMP-SET."
	::= { snStackGen 6 }




-- Stackable Management Secondary Switch Information Table


snStackSecSwitchTable OBJECT-TYPE
	SYNTAX  SEQUENCE OF SnStackSecSwitchEntry
	ACCESS  not-accessible
	STATUS  mandatory
	DESCRIPTION
		"If snSwGroupOperMode is configured as basic mode
		 which is VLAN by Port, Layer2 switching,
		 then this table is valid.  Each VLAN switch port
		 could have a number of VLAN IDs."
	::= { snStackSecSwitchInfo 1 }


snStackSecSwitchEntry OBJECT-TYPE
	SYNTAX  SnStackSecSwitchEntry
	ACCESS  not-accessible
	STATUS  mandatory
	DESCRIPTION
		"An entry in the Stackable Management Secondary Switch 
		 Information table."
	INDEX   { 
		snStackSecSwitchIndex
	}
	::= { snStackSecSwitchTable 1 }


SnStackSecSwitchEntry ::= SEQUENCE {
	snStackSecSwitchIndex
		INTEGER,
	snStackSecSwitchSlotId
		INTEGER,
	snStackSecSwitchPortCnts
		INTEGER,
	snStackSecSwitchEnabled
		INTEGER,
	snStackSecSwitchAck
		INTEGER,
	snStackSecSwitchMacAddr
		MacAddress,
	snStackSecSwitchSyncCmd
		INTEGER, 
	snStackSecSwitchIpAddr
		IpAddress,
	snStackSecSwitchSubnetMask
		IpAddress,
	snStackSecSwitchCfgCmd
		INTEGER 
	}

snStackSecSwitchIndex OBJECT-TYPE
	SYNTAX  INTEGER (1..26)
	ACCESS  read-only
	STATUS  mandatory
	DESCRIPTION
		"The secondary switch index must not be greater than the snStackMaxSecSwitch."
	::= { snStackSecSwitchEntry 1 }


snStackSecSwitchSlotId OBJECT-TYPE
	SYNTAX  INTEGER (1..26)
	ACCESS  read-write
	STATUS  mandatory
	DESCRIPTION
		"The secondary switch slot ID must be set before the Configuration 
		 command sent from the primary switch to the secondary switch 
		 either manually or automatically - snStackSecSwitchCfgCmd."
	::= { snStackSecSwitchEntry 2 }

snStackSecSwitchPortCnts OBJECT-TYPE
	SYNTAX  INTEGER (1..26)
	ACCESS  read-only
	STATUS  mandatory
	DESCRIPTION
		"The number of ports in this secondary switch."
	::= { snStackSecSwitchEntry 3 }

snStackSecSwitchEnabled OBJECT-TYPE
	SYNTAX  INTEGER {
		disabled(0),             
		enabled(1)
		}
	ACCESS  read-write
	STATUS  mandatory
	DESCRIPTION
		"The secondary switch has been selected to Stackable Management Group."
	::= { snStackSecSwitchEntry 4 }

snStackSecSwitchAck OBJECT-TYPE
	SYNTAX  INTEGER {
		disabled(0),             
		enabled(1)
		}
	ACCESS  read-only
	STATUS  mandatory
	DESCRIPTION
		"The secondary switch has sent reponse to the primary switch."
	::= { snStackSecSwitchEntry 5 }

snStackSecSwitchMacAddr OBJECT-TYPE
	SYNTAX  MacAddress
	ACCESS  read-only
	STATUS  mandatory
	DESCRIPTION
		"The secondary switch physical address. The physical address 
		represents a MAC Station."
	::= { snStackSecSwitchEntry 6 }

snStackSecSwitchSyncCmd OBJECT-TYPE
	SYNTAX  INTEGER {
		normal(0),
		invalid(1),
		device(2),
		global(3),
		local(4)
		}
	ACCESS  read-write
	STATUS  mandatory
	DESCRIPTION
		"Synchronize the secondary switches in the
		 Stackable Management Group with the following commands.
		 device(2)...........device related parameters.
		 global(3)...........global parameters.  
		 local(4)............local parameters.
		 The return result of the above commands are either
		 normal(0)...........normal condition.
		 invalid(1)...........invalid result."  
	::= { snStackSecSwitchEntry 7 }

snStackSecSwitchIpAddr OBJECT-TYPE
	SYNTAX	IpAddress
	ACCESS  read-write
	STATUS  mandatory
	DESCRIPTION
		"The secondary switch IP Address and is used for 
		 manual-command of snStackSecSwitchCfgCmd."
	::= { snStackSecSwitchEntry 8 }

snStackSecSwitchSubnetMask OBJECT-TYPE
	SYNTAX	IpAddress
	ACCESS  read-write
	STATUS  mandatory
	DESCRIPTION
		"The secondary switch IP Subnet Mask and is used for 
		 manual-command of snStackSecSwitchCfgCmd."
	::= { snStackSecSwitchEntry 9 }

snStackSecSwitchCfgCmd OBJECT-TYPE
	SYNTAX  INTEGER {
		normal(0),
		invalid(1),
		auto(2),
		manual(3)
		}
	ACCESS  read-write
	STATUS  mandatory
	DESCRIPTION
		"snStackSecSwitchSlotId must be set before the Configuration 
		 command sent from the primary switch to the secondary switch 
		 either manually or automatically.
		 auto(2)...........auto-configuration command sent.
		 manual(3).........manual-configuration command sent.
						   if manual-mode is used, snStackSecSwitchIpAddr
						   and snStackSecSwitchSubnetMask must be
						   first set before this command is sent.
		 The return result of the above commands are either
		 normal(0)...........normal condition.
		 invalid(1)..........invalid result."  
	::= { snStackSecSwitchEntry 10 }

-- System Logging Group

snAgSysLogGbl	OBJECT IDENTIFIER ::= { snAgentLog 1 }

snAgSysLogGblEnable OBJECT-TYPE
	SYNTAX	INTEGER { disabled(0), enabled(1) }
	ACCESS	read-write
	STATUS	mandatory
	DESCRIPTION
		"Enable/disable system logging."
    DEFVAL { enabled }
	::= { snAgSysLogGbl 1 }

snAgSysLogGblBufferSize OBJECT-TYPE
	SYNTAX	INTEGER (1..100)
	ACCESS	read-write
	STATUS	mandatory
	DESCRIPTION
		"The number of dynamic system logging entries."
    DEFVAL { 50 }
	::= { snAgSysLogGbl 2 }

snAgSysLogGblClear OBJECT-TYPE
	SYNTAX	INTEGER { normal(0), clearAll(1), clearDynamic(2), clearStatic(3) }
	ACCESS	read-write
	STATUS	mandatory
	DESCRIPTION
		"Clear dynamic and/or static system logging buffers."
	::= { snAgSysLogGbl 3 }

snAgSysLogGblCriticalLevel OBJECT-TYPE
	SYNTAX	INTEGER
	ACCESS	read-write
	STATUS	mandatory
	DESCRIPTION
		"Filter events going to the logging buffer. This is a packed
		bit string object of which each bit has the following meaning:
		(bit 0 is the least significant bit).

		  bit position   meaning
		  ------------   -------
		      8-31	 reserved
		      7		 Warning (warning conditions)
		      6		 Notification (normal but significant conditions)
		      5		 Informational (informational messages)
		      4		 Error (error conditions)
		      3		 Emergency (system is unusable)
		      2		 Debugging (debugging messages)
		      1		 Critical (critical conditions)
		      0		 Alert (immediate action needed)

		Setting a critical level bit to 1 makes the logging buffer
		accept the corresponding event. Resetting a critical level
		bit to 0 makes the logging buffer reject the corresponding
		event."
    DEFVAL { 255 }
	::= { snAgSysLogGbl 4 }

snAgSysLogGblLoggedCount OBJECT-TYPE
	SYNTAX	Counter
	ACCESS	read-only
	STATUS	mandatory
	DESCRIPTION
		"The number events logged in the system logging buffer."
	::= { snAgSysLogGbl 5 }

snAgSysLogGblDroppedCount OBJECT-TYPE
	SYNTAX	Counter
	ACCESS	read-only
	STATUS	mandatory
	DESCRIPTION
		"The number of events dropped."
	::= { snAgSysLogGbl 6 }

snAgSysLogGblFlushedCount OBJECT-TYPE
	SYNTAX	Counter
	ACCESS	read-only
	STATUS	mandatory
	DESCRIPTION
		"The number of times that the system logging buffer was cleared."
	::= { snAgSysLogGbl 7 }

snAgSysLogGblOverrunCount OBJECT-TYPE
	SYNTAX	Counter
	ACCESS	read-only
	STATUS	mandatory
	DESCRIPTION
		"The number of times that the system logging buffer was wrapped
		around."
	::= { snAgSysLogGbl 8 }

snAgSysLogGblServer OBJECT-TYPE
	SYNTAX  IpAddress
	ACCESS	read-write
	STATUS	deprecated
	DESCRIPTION
		"IP address of syslog server."
	::= { snAgSysLogGbl 9 }

snAgSysLogGblFacility OBJECT-TYPE
	SYNTAX  INTEGER {
		kern(1),
		user(2),
		mail(3),
		daemon(4),
		auth(5),
		syslog(6),
		lpr(7),
		news(8),
		uucp(9),
		sys9(10),
		sys10(11),
		sys11(12),
		sys12(13),
		sys13(14),
		sys14(15),
		cron(16),
		local0(17),
		local1(18),
		local2(19),
		local3(20),
		local4(21),
		local5(22),
		local6(23),
		local7(24)
		}
	ACCESS	read-write
	STATUS	mandatory
	DESCRIPTION
		"Facility code."
    DEFVAL { user }
	::= { snAgSysLogGbl 10 }

-- Dynamic System Logging Buffer Table

snAgSysLogBufferTable OBJECT-TYPE
	SYNTAX	SEQUENCE OF SnAgSysLogBufferEntry
	ACCESS	not-accessible
	STATUS	mandatory
	DESCRIPTION
		"Dynamic system logging buffer table."
	::= { snAgentLog 2 }

snAgSysLogBufferEntry OBJECT-TYPE
	SYNTAX	SnAgSysLogBufferEntry
	ACCESS	not-accessible
	STATUS	mandatory
	DESCRIPTION
		"A row in the dynamic system logging buffer table."
	INDEX	{ snAgSysLogBufferIndex }
	::= { snAgSysLogBufferTable 1 }

SnAgSysLogBufferEntry ::= SEQUENCE {
	snAgSysLogBufferIndex
		INTEGER,
	snAgSysLogBufferTimeStamp
		TimeTicks,
	snAgSysLogBufferCriticalLevel
		INTEGER,
	snAgSysLogBufferMessage
		DisplayString,
	snAgSysLogBufferCalTimeStamp
		DisplayString
	}

snAgSysLogBufferIndex OBJECT-TYPE
	SYNTAX	INTEGER (1..100)
	ACCESS	read-only
	STATUS	mandatory
	DESCRIPTION
		"The index to the dynamic system logging buffer table."
	::= { snAgSysLogBufferEntry 1 }

snAgSysLogBufferTimeStamp OBJECT-TYPE
	SYNTAX	TimeTicks
	ACCESS	read-only
	STATUS	mandatory
	DESCRIPTION
		"A time stamp when the event is logged."
	::= { snAgSysLogBufferEntry 2 }

snAgSysLogBufferCriticalLevel OBJECT-TYPE
	SYNTAX	INTEGER {
		other(1),
		alert(2),
		critical(3),
		debugging(4),
		emergency(5),
		error(6),
		informational(7),
		notification(8),
		warning(9) }
	ACCESS	read-only
	STATUS	mandatory
	DESCRIPTION
		"The critical level of this event."
	::= { snAgSysLogBufferEntry 3 }

snAgSysLogBufferMessage OBJECT-TYPE
	SYNTAX	DisplayString
	ACCESS	read-only
	STATUS	mandatory
	DESCRIPTION
		"The system logging message."
	::= { snAgSysLogBufferEntry 4 }

snAgSysLogBufferCalTimeStamp OBJECT-TYPE
	SYNTAX	DisplayString
	ACCESS	read-only
	STATUS	mandatory
	DESCRIPTION
		"A time stamp when the event is logged. This object returns
		a NULL terminated time stamp string if the system calendar
		time was set. It returns a zero length string if the system
		calendar time was not set."
	::= { snAgSysLogBufferEntry 5 }


-- Static System Logging Buffer Table

snAgStaticSysLogBufferTable OBJECT-TYPE
	SYNTAX	SEQUENCE OF SnAgStaticSysLogBufferEntry
	ACCESS	not-accessible
	STATUS	mandatory
	DESCRIPTION
		"Static system logging buffer table."
	::= { snAgentLog 3 }

snAgStaticSysLogBufferEntry OBJECT-TYPE
	SYNTAX	SnAgStaticSysLogBufferEntry
	ACCESS	not-accessible
	STATUS	mandatory
	DESCRIPTION
		"A row in the static system logging buffer table."
	INDEX	{ snAgStaticSysLogBufferIndex }
	::= { snAgStaticSysLogBufferTable 1 }

SnAgStaticSysLogBufferEntry ::= SEQUENCE {
	snAgStaticSysLogBufferIndex
		INTEGER,
	snAgStaticSysLogBufferTimeStamp
		TimeTicks,
	snAgStaticSysLogBufferCriticalLevel
		INTEGER,
	snAgStaticSysLogBufferMessage
		DisplayString,
	snAgStaticSysLogBufferCalTimeStamp
		DisplayString
	}

snAgStaticSysLogBufferIndex OBJECT-TYPE
	SYNTAX	INTEGER (1..100)
	ACCESS	read-only
	STATUS	mandatory
	DESCRIPTION
		"The index to the static system logging buffer table."
	::= { snAgStaticSysLogBufferEntry 1 }

snAgStaticSysLogBufferTimeStamp OBJECT-TYPE
	SYNTAX	TimeTicks
	ACCESS	read-only
	STATUS	mandatory
	DESCRIPTION
		"A time stamp when the event is logged."
	::= { snAgStaticSysLogBufferEntry 2 }

snAgStaticSysLogBufferCriticalLevel OBJECT-TYPE
	SYNTAX	INTEGER {
		other(1),
		alert(2),
		critical(3),
		debugging(4),
		emergency(5),
		error(6),
		informational(7),
		notification(8),
		warning(9) }
	ACCESS	read-only
	STATUS	mandatory
	DESCRIPTION
		"The critical level of this event."
	::= { snAgStaticSysLogBufferEntry 3 }

snAgStaticSysLogBufferMessage OBJECT-TYPE
	SYNTAX	DisplayString
	ACCESS	read-only
	STATUS	mandatory
	DESCRIPTION
		"The system logging message."
	::= { snAgStaticSysLogBufferEntry 4 }

snAgStaticSysLogBufferCalTimeStamp OBJECT-TYPE
	SYNTAX	DisplayString
	ACCESS	read-only
	STATUS	mandatory
	DESCRIPTION
		"A time stamp when the event is logged. This object returns
		a NULL terminated time stamp string if the system calendar
		time was set. It returns a zero length string if the system
		calendar time was not set."
	::= { snAgStaticSysLogBufferEntry 5 }

-- SysLog Server Table

snAgSysLogServerTable OBJECT-TYPE
	SYNTAX	SEQUENCE OF SnAgSysLogServerEntry
	ACCESS	not-accessible
	STATUS	mandatory
	DESCRIPTION
		"System Log Server table."
	::= { snAgentLog 4 }

snAgSysLogServerEntry OBJECT-TYPE
	SYNTAX	SnAgSysLogServerEntry
	ACCESS	not-accessible
	STATUS	mandatory
	DESCRIPTION
		"A row in the SysLog Server table."
	INDEX	{snAgSysLogServerIP, snAgSysLogServerUDPPort}
	::= { snAgSysLogServerTable 1 }

SnAgSysLogServerEntry ::= SEQUENCE {
	snAgSysLogServerIP
		IpAddress,
	snAgSysLogServerUDPPort
		INTEGER,
	snAgSysLogServerRowStatus
		INTEGER
	}

snAgSysLogServerIP OBJECT-TYPE
	SYNTAX  IpAddress
	ACCESS	read-write
	STATUS	mandatory
	DESCRIPTION
		"IP address of syslog server."
	::= { snAgSysLogServerEntry 1 }

snAgSysLogServerUDPPort       OBJECT-TYPE
	SYNTAX	INTEGER	 (0..65535)
	ACCESS  read-write
	STATUS  mandatory
	DESCRIPTION
		"UDP port number of syslog server."
	::= { snAgSysLogServerEntry 2 }

snAgSysLogServerRowStatus OBJECT-TYPE
	SYNTAX  INTEGER {
		other(1),
		valid(2),
		delete(3),
		create(4)
		}
	ACCESS  read-write
	STATUS  mandatory
	DESCRIPTION
		"This object is used to create and
		delete row in the table and control
		if they are used. The values
		that can be written are:
		  delete(3)...deletes the row
		  create(4)...creates a new row

		If the row exists, then a SET with
		value of create(4) returns error
		'badValue'. Deleted rows go away
		immediately. The following values
		can be returned on reads:
		  other(1)....some other case
		  valid(2)....the row exists and is valid"
	::= { snAgSysLogServerEntry 3 }

-- Agent System Parameters Configuration Table


snAgentSysParaConfigTable OBJECT-TYPE
	SYNTAX	SEQUENCE OF SnAgentSysParaConfigEntry
	ACCESS	not-accessible
	STATUS	mandatory
	DESCRIPTION
		"A table of Agent of each board."
	::= { snAgentSysParaConfig 1 }

snAgentSysParaConfigEntry OBJECT-TYPE
	SYNTAX	SnAgentSysParaConfigEntry
	ACCESS	not-accessible
	STATUS	mandatory
	DESCRIPTION
		"A row in the Agent System Parameters Configuation table."
	INDEX	{ snAgentSysParaConfigIndex }
	::= { snAgentSysParaConfigTable 1 }

SnAgentSysParaConfigEntry ::= SEQUENCE {
	snAgentSysParaConfigIndex
		INTEGER,
	snAgentSysParaConfigDescription
		DisplayString,
	snAgentSysParaConfigMin
		INTEGER,
	snAgentSysParaConfigMax 
		INTEGER,
	snAgentSysParaConfigDefault 
		INTEGER,
	snAgentSysParaConfigCurrent
		INTEGER
	}

snAgentSysParaConfigIndex OBJECT-TYPE
	SYNTAX	INTEGER
	ACCESS	read-only
	STATUS	mandatory
	DESCRIPTION
		"The index to the Agent System Parameters Configuation Table."
	::= { snAgentSysParaConfigEntry 1 }

snAgentSysParaConfigDescription OBJECT-TYPE
    SYNTAX DisplayString (SIZE(0..32))
    ACCESS read-only
    STATUS mandatory
    DESCRIPTION
        "The main board description string."
    ::= { snAgentSysParaConfigEntry 2 }

snAgentSysParaConfigMin OBJECT-TYPE
	SYNTAX	INTEGER
	ACCESS	read-only
	STATUS	mandatory
	DESCRIPTION
		"The minimum value of this Agent System Parameter."
	::= { snAgentSysParaConfigEntry 3 }

snAgentSysParaConfigMax OBJECT-TYPE
	SYNTAX	INTEGER
	ACCESS	read-only
	STATUS	mandatory
	DESCRIPTION
		"The maximum value of this Agent System Parameter."
	::= { snAgentSysParaConfigEntry 4 }

snAgentSysParaConfigDefault OBJECT-TYPE
	SYNTAX	INTEGER
	ACCESS	read-only
	STATUS	mandatory
	DESCRIPTION
		"The default value of this Agent System Parameter."
	::= { snAgentSysParaConfigEntry 5 }

snAgentSysParaConfigCurrent OBJECT-TYPE
	SYNTAX	INTEGER
	ACCESS	read-write
	STATUS	mandatory
	DESCRIPTION
		"The current configurated value of this Agent System Parameter."
	::= { snAgentSysParaConfigEntry 6 }


-- Agent Configured Module Table


snAgentConfigModuleTable OBJECT-TYPE
	SYNTAX	SEQUENCE OF SnAgentConfigModuleEntry
	ACCESS	not-accessible
	STATUS	mandatory
	DESCRIPTION
		"A table of each configured module information."
	::= { snAgentConfigModule 1 }

snAgentConfigModuleEntry OBJECT-TYPE
	SYNTAX	SnAgentConfigModuleEntry
	ACCESS	not-accessible
	STATUS	mandatory
	DESCRIPTION
		"A row in the Agent Configured Module table."
	INDEX	{ snAgentConfigModuleIndex }
	::= { snAgentConfigModuleTable 1 }

SnAgentConfigModuleEntry ::= SEQUENCE {
	snAgentConfigModuleIndex
		INTEGER,
	snAgentConfigModuleType
		INTEGER,
	snAgentConfigModuleRowStatus
		INTEGER,
	snAgentConfigModuleDescription
		DisplayString,
	snAgentConfigModuleOperStatus
		DisplayString,
	snAgentConfigModuleSerialNumber
		DisplayString,
	snAgentConfigModuleNumberOfPorts
		INTEGER,
	snAgentConfigModuleMgmtModuleType
		INTEGER,
	snAgentConfigModuleNumberOfCpus
		INTEGER
	}

snAgentConfigModuleIndex OBJECT-TYPE
	SYNTAX	INTEGER (1..15)
	ACCESS	read-only
	STATUS	mandatory
	DESCRIPTION
		"The index to the Agent Configured Module Table."
	::= { snAgentConfigModuleEntry 1 }

snAgentConfigModuleType OBJECT-TYPE
	SYNTAX	INTEGER	{
		bi8PortGigManagementModule(0),
		bi4PortGigManagementModule(1),
		bi16PortCopperManagementModule(2),
		bi4PortGigModule(3),
		fi2PortGigManagementModule(4),
		fi4PortGigManagementModule(5),
		bi8PortGigCopperManagementModule(6),
		fi8PortGigManagementModule(7),
		bi8PortGigModule(8),
		bi12PortGigCopper2PortGigFiberManagement(9),
		bi24PortCopperModule(10),
		fi24PortCopperModule(11),
		bi16Port100FXModule(12),
		bi8Port100FXModule(13),
		bi8PortGigCopperModule(14),
		bi12PortGigCopper2PortGigFiber(15),
		bi2PortGigManagementModule(18),
		bi24Port100FXModule(19),
		bi0PortManagementModule(20),
		pos622MbsModule(21),
		pos155MbsModule(22),
		bi2PortGigModule(23),
		bi2PortGigCopperModule(24),
		fi2PortGigModule(25),
		fi4PortGigModule(26),
		fi8PortGigModule(27),
		fi8PortGigCopperModule(28),
		fi8PortGigCopperManagementModule(29),
		pos155Mbs2PModule(30),
		fi4PortGigCopperManagementModule(31),
		fi2PortGigCopperManagementModule(32),
		bi4PortGigCopperManagementModule(33),
		bi2PortGigCopperManagementModule(34),
		bi8PortGigM4ManagementModule(35),
		bi4PortGigM4ManagementModule(36),
		bi2PortGigM4ManagementModule(37),
		bi0PortGigM4ManagementModule(38),
		bi0PortWSMManagementModule(39),
		biPos2Port2488MbsModule(40),
		bi0PortWSMModule(41),
		niPos2Port2488MbsModule(42),
		ni4802(43),
		bi4PortGigNPAModule(44),
		biAtm2Port155MbsModule(45),
		biAtm4Port155MbsModule(46),
		bi1Port10GigModule(47),
		fes4802Module(48),
		fes2402Module(49),
		fes9604Module(50),
		fes12GigCopperAndGigFiberModule(51),
		fesx24GigModule(52),
		fesx24Gig2TenGigModule(53),
		fesx24Gig1TenGigModule(54),
		fesx48GigModule(55),
		fesx48Gig2TenGigModule(56),
		fesx48Gig1TenGigModule(57),
		biFiJc48ePort100fxIpcModule(195),
		biFiJc48tPort100fxIpcModule(196),
		biFiJc8PortGigM4ManagementModule(197),
		biFiJc8PortGigIgcModule(198)
		}

    ACCESS read-write
    STATUS mandatory
    DESCRIPTION
        "The Configured Module Type."
    ::= { snAgentConfigModuleEntry 2 }


snAgentConfigModuleRowStatus OBJECT-TYPE
	SYNTAX	INTEGER	{
		other(1),
		valid(2),
		delete(3),
		create(4) }
	ACCESS	read-write
	STATUS	mandatory
	DESCRIPTION
		"To create or delete a configured module table entry."
	::= { snAgentConfigModuleEntry 3 }


snAgentConfigModuleDescription OBJECT-TYPE
	SYNTAX	DisplayString
	ACCESS	read-only
	STATUS	mandatory
	DESCRIPTION
		"A description of the configured module."
	::= { snAgentConfigModuleEntry 4 }


snAgentConfigModuleOperStatus OBJECT-TYPE
	SYNTAX	DisplayString
	ACCESS	read-only
	STATUS	mandatory
	DESCRIPTION
		"Module operational status. Zero length string indicates
		that physical module has not been inserted to the chassis."
	::= { snAgentConfigModuleEntry 5 }


snAgentConfigModuleSerialNumber OBJECT-TYPE
	SYNTAX	DisplayString
	ACCESS	read-only
	STATUS	mandatory
	DESCRIPTION
		"Module serial number. Zero length string indicates that
		module serial number EEPROM has not been programmed or
		the module does not support serial number EEPROM."
	::= { snAgentConfigModuleEntry 6 }


snAgentConfigModuleNumberOfPorts OBJECT-TYPE
	SYNTAX	INTEGER
	ACCESS	read-only
	STATUS	mandatory
	DESCRIPTION
		"The number of ports of module."
	::= { snAgentConfigModuleEntry 7 }


snAgentConfigModuleMgmtModuleType OBJECT-TYPE
	SYNTAX	INTEGER	{
		other(1),
		nonManagementModule(2),
		unknownManagementModule(3),
		m1ManagementModule(4),
		m2ManagementModule(5),
		m3ManagementModule(6),
		m4ManagementModule(7),
		m5ManagementModule(8),
		jetcoreStackManagementModule(9),
		muchoManagementModule(10),
		rottWeilerManagementModule(11),
		fesXStackManagementModule(12),
		fgsStackManagementModule(13) }
	ACCESS	read-only
	STATUS	mandatory
	DESCRIPTION
		"Management module type."
	::= { snAgentConfigModuleEntry 8 }


snAgentConfigModuleNumberOfCpus OBJECT-TYPE
	SYNTAX	INTEGER
	ACCESS	read-only
	STATUS	mandatory
	DESCRIPTION
		"The number of module CPUs."
	::= { snAgentConfigModuleEntry 9 }


-- Agent User Access Group


snAgentUserGbl OBJECT IDENTIFIER ::= { snAgentUser 1 }

snAgentUserMaxAccnt         OBJECT-TYPE
	SYNTAX	INTEGER
	ACCESS	read-only
	STATUS	mandatory
	DESCRIPTION
		"Maximum number of user account entries can be configured."
	::= { snAgentUserGbl 1 }


-- Agent User Account Table


snAgentUserAccntTable       OBJECT-TYPE
	SYNTAX	SEQUENCE OF SnAgentUserAccntEntry
	ACCESS	not-accessible
	STATUS	mandatory
	DESCRIPTION
		"A table of user account information."
	::= { snAgentUser 2 }

snAgentUserAccntEntry       OBJECT-TYPE
	SYNTAX	SnAgentUserAccntEntry
	ACCESS	not-accessible
	STATUS	mandatory
	DESCRIPTION
		"A row in the Agent User table."
	INDEX	{ snAgentUserAccntName }
	::= { snAgentUserAccntTable 1 }

SnAgentUserAccntEntry ::= SEQUENCE {
	snAgentUserAccntName
		DisplayString,
	snAgentUserAccntPassword
		DisplayString,
	snAgentUserAccntEncryptCode
		INTEGER,
	snAgentUserAccntPrivilege
		INTEGER,
	snAgentUserAccntRowStatus
		INTEGER
	}

snAgentUserAccntName        OBJECT-TYPE
    SYNTAX  DisplayString (SIZE (1..48))
	ACCESS	read-only
	STATUS	mandatory
	DESCRIPTION
		"The user name."
	::= { snAgentUserAccntEntry 1 }

snAgentUserAccntPassword    OBJECT-TYPE
	SYNTAX	DisplayString (SIZE (0..48))
	ACCESS	read-write
	STATUS	mandatory
	DESCRIPTION
		"The user password."
	::= { snAgentUserAccntEntry 2 }

snAgentUserAccntEncryptCode OBJECT-TYPE
	SYNTAX	INTEGER
	ACCESS	read-write
	STATUS	mandatory
    DESCRIPTION
        "The password encryption method code."
    ::= { snAgentUserAccntEntry 3 }

snAgentUserAccntPrivilege   OBJECT-TYPE
	SYNTAX	INTEGER
	ACCESS	read-write
	STATUS	mandatory
    DESCRIPTION
        "The user privilege."
    ::= { snAgentUserAccntEntry 4 }

snAgentUserAccntRowStatus   OBJECT-TYPE
	SYNTAX	INTEGER	{
		other(1),
		valid(2),
		delete(3),
		create(4),
		modify(5) }
	ACCESS	read-write
	STATUS	mandatory
	DESCRIPTION
		"To create or delete a user account table entry."
	::= { snAgentUserAccntEntry 5 }

-- Agent Redundant Group


snAgentRedunGbl OBJECT IDENTIFIER ::= { snAgentRedundant 1 }

snAgentRedunActiveMgmtMod      OBJECT-TYPE
	SYNTAX	INTEGER
	ACCESS	read-write
	STATUS	mandatory
	DESCRIPTION
		"Slot number of the active management module. Setting
		this object does not take effect immediately. Saving
		configuration data to flash storage and reboot the
		system are required to take effect. Setting a value of 0
		requests the system to auto-select an active management
		module after power up."
    DEFVAL { 0 }
	::= { snAgentRedunGbl 1 }

snAgentRedunSyncConfig         OBJECT-TYPE
	SYNTAX	INTEGER
	ACCESS	read-write
	STATUS	mandatory
	DESCRIPTION
		"Frequency of the backup management module copying the
		configuration data from the active management module.
		Each unit is 1 second. Setting a value 0 will disable
		the synchronization copy. Setting a negative value will
		initiate the synchronization copy once immediately."
    DEFVAL { 10 }
	::= { snAgentRedunGbl 2 }

snAgentRedunBkupCopyBootCode   OBJECT-TYPE
	SYNTAX	INTEGER { disabled(0), enabled(1) }
	ACCESS	read-write
	STATUS	mandatory
	DESCRIPTION
		"If enabled(1), the backup management module copies the boot code
		from the active management module to its boot code flash storage
		after power up, and whenever the active management module's boot
		code is updated. The backup management module does not copy if
		both boot codes were identical."
    DEFVAL { disabled }
	::= { snAgentRedunGbl 3 }

snAgentEnableMgmtModRedunStateChangeTrap OBJECT-TYPE
	SYNTAX	INTEGER { disabled(0), enabled(1) }
	ACCESS	read-write
	STATUS	mandatory
	DESCRIPTION
		"Indicates whether the SNMP agent process is permitted to
		generate management module redundancy state change traps."
    DEFVAL { enabled }
	::= { snAgentRedunGbl 4 }

snAgentRedunBkupBootLoad       OBJECT-TYPE
	SYNTAX	INTEGER {
		normal(1),
		operationError(17),
		downloadBackup(20)
		}
	ACCESS	read-write
	STATUS	mandatory
	DESCRIPTION
		"Action object to down load a new boot code from boot flash storage
		of the active management module to the backup management module.
		The following are returned values from get operation:
		  normal(1)............no operation
		  operationError(17)...error codes

		The following are input values from set operation:
		  downloadBackup(20)...download the boot code from the active
		                       management module to the backup management
		                       module

		Any set operation is rejected during loading until error
		or normal state is reached."
	::= { snAgentRedunGbl 5 }

snAgentRedunSwitchOver         OBJECT-TYPE
	SYNTAX	INTEGER {
		other(1),
		reset(2)
		}
	ACCESS	read-write
	STATUS	mandatory
	DESCRIPTION
		"To force a switch-over from standby to active state
		if the backup management module exists in a chassis."
	::= { snAgentRedunGbl 6 }

-- System CPU Utilization Table.

snAgentCpuUtilTable     OBJECT-TYPE
	SYNTAX	SEQUENCE OF SnAgentCpuUtilEntry
	ACCESS	not-accessible
	STATUS	mandatory
	DESCRIPTION
		"Table to list utilization for all CPUs in the device."
	::= { snAgentCpu 1 }

snAgentCpuUtilEntry	OBJECT-TYPE
	SYNTAX	SnAgentCpuUtilEntry
	ACCESS	not-accessible
	STATUS	mandatory
	DESCRIPTION
		"A row in the CPU utilization table."
	INDEX	{ 
		snAgentCpuUtilSlotNum,
		snAgentCpuUtilCpuId,
		snAgentCpuUtilInterval
	}
	::= { snAgentCpuUtilTable 1 }

SnAgentCpuUtilEntry ::= SEQUENCE {
	snAgentCpuUtilSlotNum
		INTEGER,
	snAgentCpuUtilCpuId
		INTEGER,
	snAgentCpuUtilInterval
		INTEGER,
	snAgentCpuUtilValue
		Gauge
	}

snAgentCpuUtilSlotNum	OBJECT-TYPE
	SYNTAX INTEGER
	ACCESS	read-only
	STATUS	mandatory
	DESCRIPTION
		"The slot number of module which contains the cpu."
	::= { snAgentCpuUtilEntry 1 }

snAgentCpuUtilCpuId  OBJECT-TYPE
	SYNTAX	INTEGER
	ACCESS	read-only
	STATUS	mandatory
	DESCRIPTION
		"The id of cpu. For non-VM1/WSM management module, there is one CPU.
		For VM1/WSM there's one management CPU and three slave CPUs.
		The management CPU could be turned off. For POS and ATM
		there's no management CPU but  two slave CPUs.
		Id for management cpu is 1. Value of 2 or greater are for slave CPUs. "
	::= { snAgentCpuUtilEntry 2 }

snAgentCpuUtilInterval  OBJECT-TYPE
	SYNTAX	INTEGER
	ACCESS	read-only
	STATUS	mandatory
	DESCRIPTION
		"The value, in seconds, for this utilization. For both management and slave CPU, we display
		utilization for 1 sec, 5 sec, 60 sec and 300 sec interval."
	::= { snAgentCpuUtilEntry 3 }

snAgentCpuUtilValue OBJECT-TYPE
	SYNTAX	Gauge
	ACCESS	read-only
	STATUS	mandatory
	DESCRIPTION
		"The statistical CPU utilization in units of one-hundredth of a percent."
	::= { snAgentCpuUtilEntry 4 }

-- System Temperarute Table.

snAgentTempTable     OBJECT-TYPE
	SYNTAX		SEQUENCE OF SnAgentTempEntry
	ACCESS	not-accessible
	STATUS		mandatory
	DESCRIPTION
		"Table to list temperatures of all the modules in the device. This
		 table is applicable to only those modules with temperature sensors."
	::= { snAgentTemp 1 }

snAgentTempEntry	OBJECT-TYPE
	SYNTAX		SnAgentTempEntry
	ACCESS	not-accessible
	STATUS		mandatory
	DESCRIPTION
		"A row in the module temperature table."
	INDEX	{ snAgentTempSlotNum, snAgentTempSensorId }
	::= { snAgentTempTable 1 }

SnAgentTempEntry ::= SEQUENCE {
	snAgentTempSlotNum
		INTEGER,
	snAgentTempSensorId
		INTEGER,
	snAgentTempSensorDescr
		DisplayString,
	snAgentTempValue
		INTEGER
	}

snAgentTempSlotNum	OBJECT-TYPE
	SYNTAX		INTEGER
	ACCESS	not-accessible
	STATUS		mandatory
	DESCRIPTION
		"The slot number of module which contains the temperature sensor
		 represented by this row."
	::= { snAgentTempEntry 1 }

snAgentTempSensorId  OBJECT-TYPE
	SYNTAX		INTEGER
	ACCESS	not-accessible
	STATUS		mandatory
	DESCRIPTION
		"The temperature sensor identifier of Slave module whose temperature is
		 represented by this row, for management module: sensor#1 -  Intake Side Temperature
		 sensor# 2 - Exhaust Side Temperature."
	::= { snAgentTempEntry 2 }

snAgentTempSensorDescr  OBJECT-TYPE
	SYNTAX		DisplayString (SIZE (0..128))
	ACCESS	read-only
	STATUS		mandatory
	DESCRIPTION
		"Describes the temperature sensor in a human readable form. This
		 is the same as snAgentTempSensorId, which is numeric and used to
		 traverse the temperature sensor table. The description provides
		 the meaning and purpose of this senor."
	::= { snAgentTempEntry 3 }

snAgentTempValue OBJECT-TYPE
    SYNTAX		INTEGER (-110..250)
	ACCESS	read-only
	STATUS		mandatory
	DESCRIPTION
		"Temperature of the the sensor represented by this row. Each unit
		 is 0.5 degrees Celcius."
	::= { snAgentTempEntry 4 }


-- Power Over Ethernet MIB Group

snAgentPoeGbl  OBJECT IDENTIFIER ::= { snAgentPoe 1 }
snAgentPoePort OBJECT IDENTIFIER ::= { snAgentPoe 2 }

-- Power Over Ethernet Global Objects

-- Power Over Ethernet Port Table

snAgentPoePortTable       OBJECT-TYPE
	SYNTAX	SEQUENCE OF SnAgentPoePortEntry
	ACCESS	not-accessible
	STATUS	mandatory
	DESCRIPTION
		"A table of POE port information."
	::= { snAgentPoePort 2 }

snAgentPoePortEntry       OBJECT-TYPE
	SYNTAX	SnAgentPoePortEntry
	ACCESS	not-accessible
	STATUS	mandatory
	DESCRIPTION
		"A row in the POE port table."
	INDEX	{ snAgentPoePortNumber }
	::= { snAgentPoePortTable 1 }

SnAgentPoePortEntry ::= SEQUENCE {
	snAgentPoePortNumber
		InterfaceIndex,
	snAgentPoePortControl
		INTEGER,
	snAgentPoePortWattage
		INTEGER,
	snAgentPoePortClass
		INTEGER,
	snAgentPoePortPriority
		INTEGER,
	snAgentPoePortConsumed
		INTEGER,
	snAgentPoePortType
		DisplayString
	}

snAgentPoePortNumber OBJECT-TYPE
    SYNTAX  InterfaceIndex
	ACCESS	read-only
	STATUS	mandatory
	DESCRIPTION
		"The port number in ifIndex value."
	::= { snAgentPoePortEntry 1 }

snAgentPoePortControl OBJECT-TYPE
	SYNTAX	INTEGER {
              other(1),
              disable(2),
              enable(3),
              enableLegacyDevice(4)
            }
	ACCESS	read-write
	STATUS	mandatory
	DESCRIPTION
		"Control inline power on/off to a port. If a port does not
		have inline power capability, reading this object returns
		'other(1)'."
	::= { snAgentPoePortEntry 2 }

snAgentPoePortWattage OBJECT-TYPE
	SYNTAX	INTEGER
	ACCESS	read-write
	STATUS	mandatory
    DESCRIPTION
		"Adjust the inline power wattage. Valid value between 1000
		to 15400. Each unit is milliwatts. This object can only be
		set after snSwIfInLinePowerControl has been set to 'enable(3)'
		or 'enableLegacyDevice(4)'. If a port does not have inline
		power capability, reading this object returns undefined value."
    ::= { snAgentPoePortEntry 3 }

snAgentPoePortClass OBJECT-TYPE
	SYNTAX	INTEGER
	ACCESS	read-write
	STATUS	mandatory
    DESCRIPTION
		"Adjust the inline power class. Valid value between 0 to 3.
		This object can only be set after snSwIfInLinePowerControl
		has been set to 'enable(3)' or 'enableLegacyDevice(4)'. If
		a port does not have inline power capability, reading this
		object returns undefined value."
    ::= { snAgentPoePortEntry 4 }

snAgentPoePortPriority OBJECT-TYPE
	SYNTAX	INTEGER	{
              invalid(0),
              critical(1),
              high(2),
              low(3),
              medium(4),
              other(5)
            }
	ACCESS	read-write
	STATUS	mandatory
	DESCRIPTION
		"Inline power allocation priority for the power device
		 0- Not a POE port, 1- Critical, 2- High, 3- Low,
		 4- Medium, 5- other."
	::= { snAgentPoePortEntry 5 }

snAgentPoePortConsumed OBJECT-TYPE
	SYNTAX	INTEGER
	ACCESS	read-only
	STATUS	mandatory
	DESCRIPTION
		"Inline power consumed by the port. Each unit is milliwatts."
	::= { snAgentPoePortEntry 6 }

snAgentPoePortType OBJECT-TYPE
	SYNTAX	DisplayString
	ACCESS	read-only
	STATUS	mandatory
	DESCRIPTION
		"Inline Power device type	802.3af or Legacy device."
	::= { snAgentPoePortEntry 7 }

END

FOUNDRY-SN-SWITCH-GROUP-MIB DEFINITIONS ::= BEGIN


-- Foundry SnSwitch Group MIB Release 2.0.0
-- Revision 0 08/18/96

-- Copyright 1996-97 Foundry Networks, Inc.
-- All rights reserved.
-- This Foundry Networks SNMP Management Information Base Specification
-- (Specification) embodies Foundry Networks' confidential and
-- proprietary intellectual property. Foundry Networks retains all
-- title and ownership in the Specification, including any
-- revisions.

-- This Specification is supplied "AS IS," and Foundry Networks makes
-- no warranty, either express or implied, as to the use,
-- operation, condition, or performance of the Specification.

-- SECTION 1: Top Level Definitions


-- Imports

IMPORTS
	Counter, TimeTicks, IpAddress, Gauge
		FROM RFC1155-SMI
	InterfaceIndex
		FROM IF-MIB
	Unsigned32, Gauge32, Counter32, Counter64
		FROM SNMPv2-SMI
	OBJECT-TYPE
		FROM RFC-1212
	snSwitch
		FROM FOUNDRY-SN-ROOT-MIB;

		-- textual conventions

	  DisplayString ::=
	      OCTET STRING
	  -- This data type is used to model textual information taken
	  -- from the NVT ASCII character set.  By convention, objects
	  -- with this syntax are declared as having
	  --
	  --      SIZE (0..255)

	  PhysAddress ::=
	      OCTET STRING
	  -- This data type is used to model media addresses.  For many
	  -- types of media, this will be in a binary representation.
	  -- For example, an ethernet address would be represented as
	  -- a string of 6 octets.

	  MacAddress ::=
	      OCTET STRING (SIZE(6))
	  -- This data type is used to model media addresses.  For many
	  -- types of media, this will be in a binary representation.
	  -- For example, an ethernet address would be represented as
	  -- a string of 6 octets.

      BridgeId ::= OCTET STRING (SIZE(8))  
      -- the Bridge-Identifier as used in the Spanning Tree

      Timeout ::= INTEGER -- a STP timer in units of 1/100 seconds

	  PortMask ::=
		  INTEGER
	  -- This data type is used to model port bitmask.  The 
	  -- maximum of ports are 32.  

      InterfaceId ::= OBJECT IDENTIFIER
	  -- This data type is used to specify an interface ID.
	  -- The first object identifier is port type, and the
	  -- format of the rest of the object identifiers depend
	  -- on the port type.
	  --
	  -- ethernet(1), format: type.slot.port
	  --   e.g. 1.3.6 is port ethernet 3/6
	  --
	  -- pos(2), format: type.slot.port
	  --   e.g. 2.10.1 is port pos 10/1
	  --
	  -- atm(3), format: type.slot.port
	  --   e.g. 3.8.2 is port atm 8/2
	  --
	  -- virtual router interface(4), format: type.ve
	  --   e.g. 4.9 is port ve 9
	  --
	  -- loopback(5), format: type.lb
	  --   e.g. 5.7 is port loopback 7
	  --
	  -- gre tunnel(6), format: type.tn, not supported
	  --
	  -- subinterface(7), format: type.slot.port.subInterface
	  --   e.g. 7.3.2.4 is port atm 3/2.4
	  --
	  -- mpls tunnel(8), format: type.tn
	  --   e.g. 8.3 is port tunnel 3
	  --
	  -- pvc(9), format: type.slot.port.subInterface.vpi.vci
	  --   e.g. 9.3.1.2.1.2 is port atm 3/1.2.1.2

-- Groups

snSwInfo 	            OBJECT IDENTIFIER ::= { snSwitch 1 }
snVLanInfo				OBJECT IDENTIFIER ::= { snSwitch 2 }
snSwPortInfo 	  		OBJECT IDENTIFIER ::= { snSwitch 3 }
snFdbInfo				OBJECT IDENTIFIER ::= { snSwitch 4 }
snPortStpInfo			OBJECT IDENTIFIER ::= { snSwitch 5 }
snTrunkInfo				OBJECT IDENTIFIER ::= { snSwitch 6 }
snSwSummary				OBJECT IDENTIFIER ::= { snSwitch 7 }
snDhcpGatewayListInfo	OBJECT IDENTIFIER ::= { snSwitch 8 }
snDnsInfo				OBJECT IDENTIFIER ::= { snSwitch 9 }
snMacFilter				OBJECT IDENTIFIER ::= { snSwitch 10 }
snNTP					OBJECT IDENTIFIER ::= { snSwitch 11 }
snRadius				OBJECT IDENTIFIER ::= { snSwitch 12 }
snTacacs				OBJECT IDENTIFIER ::= { snSwitch 13 }
snQos					OBJECT IDENTIFIER ::= { snSwitch 14 }
snAAA					OBJECT IDENTIFIER ::= { snSwitch 15 }
snCAR 					OBJECT IDENTIFIER ::= { snSwitch 16 }
snVLanCAR 				OBJECT IDENTIFIER ::= { snSwitch 17 }
snNetFlow 				OBJECT IDENTIFIER ::= { snSwitch 18 }
snSFlow 				OBJECT IDENTIFIER ::= { snSwitch 19 }
snFDP 				    OBJECT IDENTIFIER ::= { snSwitch 20 }
snVsrp   				OBJECT IDENTIFIER ::= { snSwitch 21 }
snArpInfo				OBJECT IDENTIFIER ::= { snSwitch 22 }
snWireless 				OBJECT IDENTIFIER ::= { snSwitch 23 }
snMac	 				OBJECT IDENTIFIER ::= { snSwitch 24 }
snPortMonitor			OBJECT IDENTIFIER ::= { snSwitch 25 }
snSSH					OBJECT IDENTIFIER ::= { snSwitch 26 }
snSSL					OBJECT IDENTIFIER ::= { snSwitch 27 }

-- SECTION 2: Switch Group Configuration MIBs


snSwGroupOperMode OBJECT-TYPE
	SYNTAX  INTEGER {
		noVLan(1),
	    vlanByPort(2)
		}
	ACCESS  read-write
	STATUS  mandatory
	DESCRIPTION
		"noVLan(1) represents all switch ports with no virtual 
		 LAN by port (no Port VLAN), and with no tag assigned.
		 vlanByPort(2) represents all switch ports with Basic 
		 VLAN (layer2 Switch). "
	::= { snSwInfo 1 }

snSwGroupIpL3SwMode OBJECT-TYPE
	SYNTAX  INTEGER {
		disabled(0),             
		enabled(1)
		}
	ACCESS  read-write
	STATUS  mandatory
	DESCRIPTION
		"The Switch Group is configured with the Layer3
		 IP Switch mode either enabled or disabled and the
		 default is disabled mode.
		 enabled(1)...........activate Layer3 IP Switch
		 disabled(0)..........disable Layer3 IP Switch"  
	::= { snSwInfo 2 }


snSwGroupIpMcastMode OBJECT-TYPE
	SYNTAX  INTEGER {
		disabled(0),
		enabled(1)
		}
	ACCESS  read-write
	STATUS  mandatory
	DESCRIPTION
		"The Switch Group is configured with the IP Multicast
		 pruning mode either enabled or disabled and the
		 default is disabled mode.
		 enabled(1)...........activate IP Multicast pruning
		 disabled(0)..........no IP Multicast pruning"
	::= { snSwInfo 3 }


snSwGroupDefaultCfgMode OBJECT-TYPE
	SYNTAX  INTEGER {
		default(1),
		nonDefault(2)
		}
	ACCESS  read-write
	STATUS  mandatory
	DESCRIPTION
		"The Switch Group is configured with the Default
		 configuration. If the default configuration gets
		 overwritten, the state will change to non-default.
		 default(1)...........default configuration
		 nonDefault(2)..........non default configuration"
	::= { snSwInfo 4 }


snSwGroupSwitchAgeTime OBJECT-TYPE
	SYNTAX  INTEGER
	ACCESS  read-write
	STATUS  mandatory
	DESCRIPTION
		"The Switch Age time is 180sec by default.
		 The configured range is 10 to 10,000sec.  The time
		 represents the time span to age out an MAC Address
		 entry."
	::= { snSwInfo 5 }



snVLanGroupVlanCurEntry OBJECT-TYPE
	SYNTAX  INTEGER
	ACCESS  read-only
	STATUS  mandatory
	DESCRIPTION
		"The current total entry number of VLANs are configured." 
	::= { snSwInfo 6 }


snVLanGroupSetAllVLan OBJECT-TYPE
	SYNTAX  INTEGER
	ACCESS  read-write
	STATUS  mandatory
	DESCRIPTION
		"The value of this object is the VLanIndex of a particalur
		 entry in snVLanByPortCfgTable (snVLanByPortCfgVLanId).  
		 All the attributes of that row of table except PortMask
		 will be used to set the same attributes for the 
		 entire VLan group. VLanId and PortMask must be set for 
                 that particular entry prior to setting this object.
		 Switch software will base on that VLAN information
		 to set the entire VLAN.   
		 Note: All the intended attributes of the given 
		 row of the table (given VLAN) must be set prior
		 setting this object.  When this object is set,
		 Set-All-VLAN action will take place simultaneously.
		 The previous setting will be overwritten by the 
		 new one."
	::= { snSwInfo 7 }


snSwPortSetAll OBJECT-TYPE
	SYNTAX  INTEGER
	ACCESS  read-write
	STATUS  mandatory
	DESCRIPTION
		"The value of this object is the index number of the
		 snSwPortInfoTable (snSwPortInfoPortIndex).  
		 snSwPortInfoMonitorMode, snSwPortInfoTagMode, 
		 snSwPortInfoChnMode, snSwPortInfoSpeed,
		 snSwPortInfoAdminStatus are all the
		 read-write attributes of that row of table.
		 They will be used to set the same attributes for
		 all the ports in the system.
		 Note: prior setting this object, all the intended 
		 attributes of the given row of the table must be set.  
		 Otherwise, the current data of the row will be used to 
		 set the entire port-table. The previous setting will
		 be overwritten by the new one." 
	::= { snSwInfo 8 }



snFdbTableCurEntry OBJECT-TYPE
	SYNTAX  INTEGER
	ACCESS  read-only
	STATUS  mandatory
	DESCRIPTION
		"The current total entry number of FDB are configured." 
	::= { snSwInfo 9 }


snFdbTableStationFlush OBJECT-TYPE
	SYNTAX  INTEGER {
	    normal(1),
        error(2),
        flush(3),
        flushing(4)
	}
	ACCESS  read-write
	STATUS  mandatory
	DESCRIPTION
		"The following values of the flush state
		 can only be read:
		  normal(1)... normal state
		  error(2)... operation failed
		  flushing(4)... in process

		The following value can be written:
		  flush(3).....do flush 

		The agent will return a response even before the flush is done.
		And the read value will be flushing until flush is done.
		And the flush request will be rejected until error or normal."
	::= { snSwInfo 10 }


snPortStpSetAll OBJECT-TYPE
	SYNTAX  INTEGER
	ACCESS  read-write
	STATUS  mandatory
	DESCRIPTION
		"The value of this object is 1 which means invoking
                 Port STP Set-all command.  The snPortStpPriority, 
                 snPortStpPathCost, the read-write STP related 
                 attributes of the first row of table will be used 
                 to set the same attributes for all the ports in the 
                 system. 
		 Note: prior setting this object, all the intended 
		 attributes of the given row of the table must be set.  
		 Otherwise, the current data of the row will be used to 
		 set the entire port-table. The previous setting will
		 be overwritten by the new one." 
	::= { snSwInfo 11 }


snSwProbePortNum OBJECT-TYPE
	SYNTAX  INTEGER
	ACCESS  read-write
	STATUS  mandatory
	DESCRIPTION
		"A chassis switch probe port is operated as a traffic analyzer
		 port and only one port can be assigned in the chassis.
		 The bit 0 to bit 7: port number. 
		 The bit 8 to bit 11: slot number.
		 A stackable switch is only assigned with one probe port as a 
		 traffic analyzer."
	::= { snSwInfo 12 }


snSw8021qTagMode OBJECT-TYPE
	SYNTAX  INTEGER {
		disabled(0),
		enabled(1)
		}
	ACCESS  read-write
	STATUS  mandatory
	DESCRIPTION
		"The Switch Group is configured with the IEEE802.1q
		 Tagging mode either enabled or disabled and the
		 default is disabled mode.
		 enabled(1)...........activate IEEE802.1q Tagging mode.
		 disabled(0)..........no IEEE802.1q Tagging."
	::= { snSwInfo 13 }


snSwGlobalStpMode OBJECT-TYPE
	SYNTAX  INTEGER {
		disabled(0),
		enabled(1)       
		}
	ACCESS  read-write
	STATUS  mandatory
	DESCRIPTION
		"Spanning Tree System Global Mode in the Switch Group 
		 can be set either enabled or disabled and the default is 
		 enabled mode.
		 enabled(1)...........activate Spanning Tree
		 disabled(0)..........no Spanning Tree"
	::= { snSwInfo 14 }


snSwIpMcastQuerierMode OBJECT-TYPE
	SYNTAX  INTEGER {
		querier(1),
		nonQuerier(2)
		}
	ACCESS  read-write
	STATUS  mandatory
	DESCRIPTION
		"The IP Multicast pruning mode is configured either 
		 Non-Querier or Querier mode and the default is 
		 querier mode.
		 querier(1)...........when prunning traffic locally 
		                      within the VLAN.
		 nonQuerier(2)........when running with a multicast 
		                      capable router in the network."
	::= { snSwInfo 15 }

snSwViolatorPortNumber OBJECT-TYPE
	SYNTAX	INTEGER
	ACCESS  read-only
	STATUS	mandatory
	DESCRIPTION
		"The port number of the switch or router that received
		 a violator packet. It is included in the locked
		 address violation trap.
		 The bit 0 to bit 7: port number. 
		 The bit 8 to bit 11: slot number (slot for chassis only)."
	::= { snSwInfo 17 }

snSwViolatorMacAddress OBJECT-TYPE
    SYNTAX  MacAddress
	ACCESS  read-only
	STATUS	mandatory
	DESCRIPTION
		"The source address of the violator packet received
		 by the switch or router. It is included in the locked
		 address violation trap."
	::= { snSwInfo 18 }

snVLanGroupVlanMaxEntry OBJECT-TYPE
	SYNTAX  INTEGER
	ACCESS  read-write
	STATUS  mandatory
	DESCRIPTION
		"The maximum number of VLAN entries are allowed to configure."
	::= { snSwInfo 19 }

snSwEosBufferSize OBJECT-TYPE
	SYNTAX  INTEGER
	ACCESS  read-only
	STATUS  mandatory
	DESCRIPTION
		"A specific buffer size for all the different EOS buffers."
	::= { snSwInfo 20 }

snVLanByPortEntrySize OBJECT-TYPE
	SYNTAX  INTEGER 
	ACCESS  read-only
	STATUS  mandatory
	DESCRIPTION
		 "The size of each VLAN table entry."
	::= { snSwInfo 21 }

snSwPortEntrySize OBJECT-TYPE
	SYNTAX  INTEGER 
	ACCESS  read-only
	STATUS  mandatory
	DESCRIPTION
		 "The size of each port table entry."
	::= { snSwInfo 22 }

snFdbStationEntrySize OBJECT-TYPE
	SYNTAX  INTEGER 
	ACCESS  read-only
	STATUS  mandatory
	DESCRIPTION
		 "The size of each Fdb station table entry."
	::= { snSwInfo 23 }

snPortStpEntrySize OBJECT-TYPE
	SYNTAX  INTEGER 
	ACCESS  read-only
	STATUS  mandatory
	DESCRIPTION
		 "The size of each port stp table entry."
	::= { snSwInfo 24 }

snSwEnableBridgeNewRootTrap OBJECT-TYPE
	SYNTAX	INTEGER { disabled(0), enabled(1) }
	ACCESS	read-write
	STATUS	mandatory
	DESCRIPTION
		"Indicates whether the SNMP agent process is
		permitted to generate bridge new root traps."
    DEFVAL { enabled }
	::= { snSwInfo 25 }

snSwEnableBridgeTopoChangeTrap OBJECT-TYPE
	SYNTAX	INTEGER { disabled(0), enabled(1) }
	ACCESS	read-write
	STATUS	mandatory
	DESCRIPTION
		"Indicates whether the SNMP agent process is
		permitted to generate bridge topology change
		traps."
    DEFVAL { enabled }
	::= { snSwInfo 26 }

snSwEnableLockedAddrViolationTrap OBJECT-TYPE
	SYNTAX	INTEGER { disabled(0), enabled(1) }
	ACCESS	read-write
	STATUS	mandatory
	DESCRIPTION
		"Indicates whether the SNMP agent process is
		permitted to generate locked address violation
		traps."
    DEFVAL { enabled }
	::= { snSwInfo 27 }

snSwIpxL3SwMode OBJECT-TYPE
	SYNTAX  INTEGER {
		disabled(0),             
		enabled(1)
		}
	ACCESS  read-write
	STATUS  mandatory
	DESCRIPTION
		"The Switch Group is configured with the Layer3
		 IPX Switch mode either enabled or disabled and 
		 the default is disabled mode.
		 enabled(1)...........activate Layer3 Switch
		 disabled(0)..........disable Layer3 Switch"  
	::= { snSwInfo 28 }

snVLanByIpSubnetMaxSubnets OBJECT-TYPE
	SYNTAX  INTEGER 
	ACCESS  read-only
	STATUS  mandatory
	DESCRIPTION
		"The maximum number of subnets for each IP VLAN."
	::= { snSwInfo 29 }

snVLanByIpxNetMaxNetworks OBJECT-TYPE
	SYNTAX  INTEGER 
	ACCESS  read-only
	STATUS  mandatory
	DESCRIPTION
		"The maximum number of networks for each IPX VLAN."
	::= { snSwInfo 30 }

snSwProtocolVLanMode OBJECT-TYPE
	SYNTAX  INTEGER {
		disabled(0),
	    enabled(1)
		}
	ACCESS  read-write
	STATUS  deprecated
	DESCRIPTION
		"disabled(0) - represents system with Protocol VLAN disabled. 
		 enabled(1) - represents system with Protocol VLAN enabled (Layer3 VLAN)."
	::= { snSwInfo 31 }

snMacStationVLanId OBJECT-TYPE
	SYNTAX  INTEGER (0..4095)
	ACCESS  read-write
	STATUS  deprecated
	DESCRIPTION
		"This VLAN ID controls filtering of the Forwarding Database
		table in the standard Bridge MIB (dot1dTpFdbTable).  Since the
		dot1dTpFdbTable contains MAC addresses associated with each of
		the ports in the bridge, and each MAC address can be
		associated with different VLANs, the snMacStationVLanId can be
		used by users to specify which VLAN's MAC Station information
		the dot1dTpFdbTable should provide.  If this variable is set
		to zero (the default value), all MAC station entries will be
		returned when the dot1dTpFdbTable is retrieved.  The
		VLAN-aware dot1qTpFdbTable described in RFC 2674 should be
		used as a replacement for this variable."
	::= { snSwInfo 32 }

snSwClearCounters OBJECT-TYPE
	SYNTAX  INTEGER {
		valid(0),
	    clear(1)
		}
	ACCESS  read-write
	STATUS  mandatory
	DESCRIPTION
		"valid(0) - a SNMP-GET of this mib shows that it is valid command to use. 
		 clear(1) - represents clear counter command of the following counters:
		 			Dot3, MIB2, IP and IPX counters for all ports."
	::= { snSwInfo 33 }

snSw8021qTagType OBJECT-TYPE
	SYNTAX  INTEGER
	ACCESS  read-write
	STATUS  mandatory
	DESCRIPTION
		"The IEEE802.1q tag type embedded in the length/type field of
		an Ethernet packet. It specifies that the 2 octets after the
		length/type field in an Ethernet packet is the tag value."
    DEFVAL { 33024 }
	::= { snSwInfo 34 }

snSwBroadcastLimit OBJECT-TYPE
	SYNTAX  INTEGER
	ACCESS  read-write
	STATUS  mandatory
	DESCRIPTION
		"Limit the number of broadcast packets to forward out of the
		switch ports. This object specifies the number of broadcast
		packets per second. Setting a value of 0 to this object
		disables the limitation check."
    DEFVAL { 0 }
	::= { snSwInfo 35 }

snSwMaxMacFilterPerSystem  OBJECT-TYPE
	SYNTAX  INTEGER 
	ACCESS  read-only
	STATUS  mandatory
	DESCRIPTION
		"The maximum number of MAC Filters per system in the MAC Filter table."
	::= { snSwInfo 36 }

snSwMaxMacFilterPerPort  OBJECT-TYPE
	SYNTAX  INTEGER 
	ACCESS  read-only
	STATUS  mandatory
	DESCRIPTION
		"The maximum number of MAC Filters per port in the Port MAC Access Filter table."
	::= { snSwInfo 37 }

snSwDefaultVLanId OBJECT-TYPE
	SYNTAX  INTEGER (1..4095)
	ACCESS  read-write
	STATUS  mandatory
	DESCRIPTION
		"The VLAN ID of the DEFAULT PORT-VLAN."
	::= { snSwInfo 38 }

snSwGlobalAutoNegotiate OBJECT-TYPE
	SYNTAX  INTEGER {
		disabled(0),
		enabled(1),
		negFullAuto(2),
		other(3)
		}
	ACCESS  read-write
	STATUS  mandatory
	DESCRIPTION
		"This feature only applies to Gigabit Ethernet ports. If set
		to disable(0), all Gigabit Ethernet ports will be put to non-
		negotiation mode. If set to enable(1), all Gigabit Ethernet
		ports will start auto-negotiation indefinitely until succeed.
		If set to negFullAuto(2), all Gigabit Ethernet ports will start
		with auto-negotiation, if the negotiation failed, then they
		will automatically switch to non-negotiation mode. Stackable
		products (except TurboIron 8) Gigabit Ethernet ports do not
		support negFullAuto(2). If the snSwPortInfoAutoNegotiate value
		of a port was not set to global, this global value does not
		apply to the negotiation mode of that port."
    DEFVAL { negFullAuto }
	::= { snSwInfo 39 }

snSwQosMechanism OBJECT-TYPE
	SYNTAX	INTEGER { strict(0), weighted(1) }
	ACCESS	read-write
	STATUS	mandatory
	DESCRIPTION
		"Indicates whether the qos mechanism is
		 strict or weighted."
    DEFVAL { weighted }
	::= { snSwInfo 40 }

snSwSingleStpMode OBJECT-TYPE
	SYNTAX  INTEGER {
		disabled(0),
		enabled(1)       
		}
	ACCESS  read-write
	STATUS  mandatory
	DESCRIPTION
		"Single Spanning Tree System Mode in the Switch Group 
		 can be set either enabled or disabled and the default is 
		 disabled mode.
		 enabled(1)...........activate Single Spanning Tree
		 disabled(0)..........no Single Spanning Tree"
	::= { snSwInfo 41 }

snSwFastStpMode OBJECT-TYPE
	SYNTAX  INTEGER {
		disabled(0),
		enabled(1)       
		}
	ACCESS  read-write
	STATUS  mandatory
	DESCRIPTION
		"Fast Spanning Tree System Mode in the Switch Group 
		 can be set either enabled or disabled and the default is 
		 enabled mode.
		 enabled(1)...........activate Fast Spanning Tree
		 disabled(0)..........no Fast Spanning Tree"
	::= { snSwInfo 42 }

snSwViolatorIfIndex OBJECT-TYPE
	SYNTAX	INTEGER
	ACCESS  read-only
	STATUS  mandatory
	DESCRIPTION
		"The port number of the switch or router that received
		 a violator packet. It is included in the locked
		 address violation trap."
	::= { snSwInfo 43 }

snSwSingleStpVLanId OBJECT-TYPE
	SYNTAX  INTEGER
	ACCESS  read-only
	STATUS  mandatory
	DESCRIPTION
		"The VLAN ID of the Single Spanning Tree VLAN if Single
		Spanning Tree was enabled. This object returns zero if
		Single Spanning Tree was disabled."
	::= { snSwInfo 44 }


-- VLAN Layer 2 Switch VLAN By Port Information Table


snVLanByPortTable OBJECT-TYPE
	SYNTAX  SEQUENCE OF SnVLanByPortEntry
	ACCESS  not-accessible
	STATUS  deprecated
	DESCRIPTION
		"If snSwGroupOperMode is configured as basic mode
		 which is VLAN by Port, Layer2 switching,
		 then this table is valid.  Each VLAN switch port
		 could have a number of VLAN IDs."
	::= { snVLanInfo 1 }


snVLanByPortEntry OBJECT-TYPE
	SYNTAX  SnVLanByPortEntry
	ACCESS  not-accessible
	STATUS  deprecated
	DESCRIPTION
		"An entry in the VLAN By Port Information table.
		 snVLanByPortVLanIndex = 1 and with 
		 snVLanByPortVLanId = 1 together implies all attributes
		 applying to the Global switch group i.e. noVLan.
		 A SNMP SET PDU for a row of the snVLanByPortTable 
		 requires the entired sequence of the MIB Objects in each 
		 snVLanByPortEntry stored in one PDU.  Otherwise, 
	 GENERR return-value will be returned."
	INDEX   { 
		snVLanByPortVLanIndex
	}
	::= { snVLanByPortTable 1 }


SnVLanByPortEntry ::= SEQUENCE {
	snVLanByPortVLanIndex
		INTEGER,
	snVLanByPortVLanId
		INTEGER,
	snVLanByPortPortMask
		PortMask,
	snVLanByPortQos
		INTEGER,
	snVLanByPortStpMode
		INTEGER,
	snVLanByPortStpPriority 
     	INTEGER,
	snVLanByPortStpGroupMaxAge 
		INTEGER,
	snVLanByPortStpGroupHelloTime 
		INTEGER,
	snVLanByPortStpGroupForwardDelay 
		INTEGER,
	snVLanByPortRowStatus 
		INTEGER,
	snVLanByPortOperState
		INTEGER,
	snVLanByPortBaseNumPorts
    	INTEGER,
	snVLanByPortBaseType
    	INTEGER, 
	snVLanByPortStpProtocolSpecification 
     	INTEGER,
	snVLanByPortStpMaxAge
     	Timeout,
	snVLanByPortStpHelloTime 
     	Timeout,
	snVLanByPortStpHoldTime 
     	INTEGER,
 	snVLanByPortStpForwardDelay 
       	Timeout,
	snVLanByPortStpTimeSinceTopologyChange 
     	TimeTicks,
	snVLanByPortStpTopChanges
      	Counter,
	snVLanByPortStpRootCost
    	INTEGER,
	snVLanByPortStpRootPort
    	INTEGER,
	snVLanByPortStpDesignatedRoot
     	BridgeId,
    snVLanByPortBaseBridgeAddress 
        MacAddress,
	snVLanByPortVLanName
		DisplayString,
    snVLanByPortRouterIntf
	    INTEGER,
	snVLanByPortChassisPortMask
		OCTET STRING,
	snVLanByPortPortList
		OCTET STRING
	}

snVLanByPortVLanIndex OBJECT-TYPE
	SYNTAX  INTEGER (1..4095)
	ACCESS  read-only
	STATUS  deprecated
	DESCRIPTION
		"The VLAN ID index must not be greater than the 
		 snVLanGroupVlanMaxEntry. Each VLAN Identifier can 
		 have a membership of multiple ports."
	::= { snVLanByPortEntry 1 }


snVLanByPortVLanId OBJECT-TYPE
	SYNTAX  INTEGER (1..4095)
	ACCESS  read-write
	STATUS  deprecated
	DESCRIPTION
		"The VLAN ID index to the VLAN By Port Info Table.
		 Each VLAN Identifier can have a membership of multiple 
		 ports."
	::= { snVLanByPortEntry 2 }


snVLanByPortPortMask OBJECT-TYPE
	SYNTAX  PortMask
	ACCESS  read-write
	STATUS  deprecated
	DESCRIPTION
		"The Standand-alone switch VLAN port membership. (It was obsoleted for Chassis Product)"
	::= { snVLanByPortEntry 3 }


snVLanByPortQos OBJECT-TYPE
	SYNTAX  INTEGER {
		level0(0),
		level1(1),
		level2(2),
		level3(3),
		level4(4),
		level5(5),
		level6(6),
		level7(7)
		}
	ACCESS  read-write
	STATUS  deprecated
	DESCRIPTION
		"The Stand alone stackable switch VLAN Priority values are:
		 low(0)   -- low prority
		 high(1) -- high prority.
		 The BigIron switch VLAN Priority values are:
		level0(0), level1(1), level2(2), level3(3),
		level4(4), level5(5), level6(6), level7(7) "
	::= { snVLanByPortEntry 4 }

snVLanByPortStpMode OBJECT-TYPE
	SYNTAX  INTEGER {
		disable(0),
		enableStp(1),
		enableRstp(2)
		}
	ACCESS  read-write
	STATUS  deprecated
	DESCRIPTION
		"Spanning Tree Mode in the Switch Group can be set
		 either enabled or disabled and the default is 
		 enabled mode.
		 disable(0)...........no Spanning Tree
		 enableStp(1).........activate Spanning Tree
		 enableRstp(2)........activate Rapid Spanning Tree"
	::= { snVLanByPortEntry 5 }

snVLanByPortStpPriority OBJECT-TYPE
    SYNTAX  INTEGER (1..65535)
    ACCESS  read-write
    STATUS  deprecated
    DESCRIPTION
	"dot1dStpPriority : The value of the write-able 
	 portion of the Stp ID, i.e., the first two octets 
	 of the (8 octet long) Bridge ID.  The other (last) 6 
	 octets of the Bridge ID are given by the value of the 
	 base bridge address - dot1dBaseBridgeAddress."
	::= { snVLanByPortEntry 6 }

snVLanByPortStpGroupMaxAge OBJECT-TYPE
	SYNTAX  INTEGER (6..40)
    ACCESS  read-write
    STATUS  deprecated
    DESCRIPTION
    "dot1dStpBridgeMaxAge: From RFC1493(Bridge MIB).
     The value that all bridges use for MaxAge when 
     this bridge is acting as the root. 
     Note that 802.1D-1990 specifies that the 
     range for this parameter is related to the value of
     dot1dStpBridgeHelloTime. The granularity of this
     timer is specified by 802.1D-1990 to be 1 second.
     An agent may return a badValue error if a set is
     attempted to a value which is not a whole number
     of seconds."
	::= { snVLanByPortEntry 7 }

snVLanByPortStpGroupHelloTime OBJECT-TYPE
    SYNTAX  INTEGER (1..10)
    ACCESS  read-write
    STATUS  deprecated
    DESCRIPTION
    "dot1dStpBridgeHelloTime: From RFC1493(Bridge MIB).
     The value that all bridges use for HelloTime when
     this bridge is acting as the root.  The
     granularity of this timer is specified by 802.1D-
     1990 to be 1 second.  An agent may return a
     badValue error if a set is attempted to a value
     which is not a whole number of seconds."
	::= { snVLanByPortEntry 8 }

snVLanByPortStpGroupForwardDelay OBJECT-TYPE
	SYNTAX  INTEGER (2..30)
    ACCESS  read-write
    STATUS  deprecated
    DESCRIPTION
	"dot1dStpBridgeForwardDelay : From RFC1493(Bridge MIB).
     The value that all bridges use for ForwardDelay
     when this bridge is acting as the root.  Note that
     802.1D-1990 specifies that the range for this
     parameter is related to the value of
     dot1dStpBridgeMaxAge.  The granularity of this
     timer is specified by 802.1D-1990 to be 1 second.
     An agent may return a badValue error if a set is
     attempted to a value which is not a whole number
     of seconds."
	::= { snVLanByPortEntry 9 }

snVLanByPortRowStatus OBJECT-TYPE
	SYNTAX  INTEGER {
		other(1),
		valid(2),
		delete(3),
		create(4),
		modify(5)
		}
	ACCESS  read-write
	STATUS  deprecated
	DESCRIPTION
		"This object is used to create and
		delete row in the table and control
		if they are used. The values
		that can be written are:
		  delete(3)...deletes the row
		  create(4)...creates a new row
		  modify(5)...modifies an exsisting row

		If the row exists, then a SET with
		value of create(4) returns error
		'badValue'. Deleted rows go away
		immediately. The following values
		can be returned on reads:
		  noSuch(0)...no such row
		  other(1)....some other case
		  valid(2)....the row exists and is valid"
	::= { snVLanByPortEntry 10 }

snVLanByPortOperState OBJECT-TYPE
	SYNTAX  INTEGER {
		notActivated(0),             
		activated(1)
		}
	ACCESS  read-only
	STATUS  deprecated
	DESCRIPTION
		"By default, this mode is set to notActivated(0).
		 notActivated(0)...the VLAN entry is not activated and not in running mode.
		 activated(1)......the VLAN entry is activated and in running mode"  
	::= { snVLanByPortEntry 11 }

snVLanByPortBaseNumPorts OBJECT-TYPE
    SYNTAX  INTEGER
    ACCESS  read-only
    STATUS  deprecated
    DESCRIPTION
    "The number of ports controlled by this bridging
     entity."
	::= { snVLanByPortEntry 12 }

snVLanByPortBaseType OBJECT-TYPE
    SYNTAX  INTEGER {
              unknown(1),
              transparent-only(2),
              sourceroute-only(3),
              srt(4)
            }
    ACCESS  read-only
    STATUS  deprecated
    DESCRIPTION
    "Indicates what type of bridging this bridge can
     perform.  If a bridge is actually performing a
     certain type of bridging this will be indicated by
     entries in the port table for the given type."
	::= { snVLanByPortEntry 13 }

snVLanByPortStpProtocolSpecification OBJECT-TYPE
    SYNTAX  INTEGER {
        unknown(1),
        decLb100(2),
        ieee8021d(3)
        }
    ACCESS  read-only
    STATUS  deprecated
    DESCRIPTION
    "An indication of what version of the Spanning
     Tree Protocol is being run.  The value
     'decLb100(2)' indicates the DEC LANbridge 100
     Spanning Tree protocol.  IEEE 802.1d
     implementations will return 'ieee8021d(3)'.  If
     future versions of the IEEE Spanning Tree Protocol
     are released that are incompatible with the
     current version a new value will be defined."
	::= { snVLanByPortEntry 14 }


snVLanByPortStpMaxAge OBJECT-TYPE
    SYNTAX  Timeout
    ACCESS  read-only
    STATUS  deprecated
    DESCRIPTION
    "dot1dStpMaxAge: From RFC1493(Bridge MIB).
     The maximum age of Spanning Tree Protocol
     information learned from the network on any port
     before it is discarded, in units of hundredths of
     a second.  This is the actual value that this
     bridge is currently using."
	::= { snVLanByPortEntry 15 }

snVLanByPortStpHelloTime OBJECT-TYPE
    SYNTAX  Timeout
    ACCESS  read-only
    STATUS  deprecated
    DESCRIPTION
    "dot1dStpHelloTime: From RFC1493(Bridge MIB).
     The amount of time between the transmission of
     Configuration bridge PDUs by this node on any port
     when it is the root of the spanning tree or trying
     to become so, in units of hundredths of a second.
     This is the actual value that this bridge is
     currently using."
	::= { snVLanByPortEntry 16 }

snVLanByPortStpHoldTime OBJECT-TYPE
    SYNTAX  INTEGER
    ACCESS  read-only
    STATUS  deprecated
    DESCRIPTION
    "dot1dStpHoldTime: From RFC1493(Bridge MIB).
     This time value determines the interval length
     during which no more than two Configuration bridge
     PDUs shall be transmitted by this node, in units
     of hundredths of a second."
	::= { snVLanByPortEntry 17 }

 snVLanByPortStpForwardDelay OBJECT-TYPE
     SYNTAX  Timeout
     ACCESS  read-only
     STATUS  deprecated
     DESCRIPTION
     "dot1dStpForwardDelay: From RFC1493(Bridge MIB).
      This time value, measured in units of hundredths
      of a second, controls how fast a port changes its
      spanning state when moving towards the Forwarding
      state.  The value determines how long the port
      stays in each of the Listening and Learning
      states, which precede the Forwarding state.  This
      value is also used, when a topology change has
      been detected and is underway, to age all dynamic
      entries in the Forwarding Database.  [Note that
      this value is the one that this bridge is
      currently using, in contrast to
      dot1dStpBridgeForwardDelay which is the value that
      this bridge and all others would start using
      if/when this bridge were to become the root.]"
	::= { snVLanByPortEntry 18 }


snVLanByPortStpTimeSinceTopologyChange OBJECT-TYPE
    SYNTAX  TimeTicks
    ACCESS  read-only
    STATUS  deprecated
    DESCRIPTION
    "The time (in hundredths of a second) since the
     last time a topology change was detected by the
     bridge entity."
	::= { snVLanByPortEntry 19 }

snVLanByPortStpTopChanges OBJECT-TYPE
    SYNTAX  Counter
    ACCESS  read-only
    STATUS  deprecated
    DESCRIPTION
    "The total number of topology changes detected by
     this bridge since the management entity was last
     reset or initialized."
	::= { snVLanByPortEntry 20 }

snVLanByPortStpRootCost OBJECT-TYPE
    SYNTAX  INTEGER
    ACCESS  read-only
    STATUS  deprecated
    DESCRIPTION
    "dot1dStpRootCost: From RFC1493(Bridge MIB).     
     The cost of the path to the root as seen from
     this bridge."
	::= { snVLanByPortEntry 21 }

snVLanByPortStpRootPort OBJECT-TYPE
    SYNTAX  INTEGER
    ACCESS  read-only
    STATUS  deprecated
    DESCRIPTION
    "dot1dStpRootPort: From RFC1493(Bridge MIB).
     The port number of the port which offers the
     lowest cost path from this bridge to the root
     bridge."
	::= { snVLanByPortEntry 22 }

snVLanByPortStpDesignatedRoot OBJECT-TYPE
    SYNTAX  BridgeId
    ACCESS  read-only
    STATUS  deprecated
    DESCRIPTION
    "dot1dStpDesignatedRoot: From RFC1493(Bridge MIB).
     The bridge identifier of the root of the spanning
     tree as determined by the Spanning Tree Protocol
     as executed by this node.  This value is used as
     the Root Identifier parameter in all Configuration
     Bridge PDUs originated by this node."
	::= { snVLanByPortEntry 23 }

snVLanByPortBaseBridgeAddress OBJECT-TYPE
    SYNTAX  MacAddress
    ACCESS  read-only
    STATUS  deprecated
    DESCRIPTION
    "The MAC address used by this bridge when it must
     be referred to in a unique fashion.   It is
     recommended that this be the numerically smallest
     MAC address of all ports that belong to this
     bridge.  However it is only required to be unique.
     When concatenated with dot1dStpPriority a unique
     BridgeIdentifier is formed which is used in the
     Spanning Tree Protocol."
	::= { snVLanByPortEntry 24 }

snVLanByPortVLanName OBJECT-TYPE
	SYNTAX	DisplayString (SIZE(0..32))
	ACCESS	read-write
	STATUS	deprecated
	DESCRIPTION
		"VLAN Community Name string."
	::= { snVLanByPortEntry 25 }


snVLanByPortRouterIntf OBJECT-TYPE
	SYNTAX  INTEGER (1..60)
	ACCESS  read-write
	STATUS  deprecated
	DESCRIPTION
		"Optional: A virtual interface for router to the VLAN -- applied to router only.
		 If a SNMP-Get value is zero, that means this object was not configured."
	::= { snVLanByPortEntry 26 }


snVLanByPortChassisPortMask OBJECT-TYPE
	SYNTAX  OCTET STRING (SIZE(32))
	ACCESS  read-write
	STATUS  deprecated
	DESCRIPTION
		"The Chassis VLAN switch port membership.
		(It was obsoleted after release 07100, replaced by snVLanByPortPortList)"
	::= { snVLanByPortEntry 27 }

snVLanByPortPortList OBJECT-TYPE
	SYNTAX  OCTET STRING
	ACCESS  read-write
	STATUS  deprecated
	DESCRIPTION
		"A list of port indices which are the port
		membership of a VLAN By Port. Each port index is a
		16-bit integer in big endian order. 8-bit is the slot number,
		the other 8-bit is the port number."
	::= { snVLanByPortEntry 28 }


-- Port VLAN (Layer 2 VLAN) Port Membership Table
-- Use this table to create or delete a VLAN entry


snVLanByPortMemberTable OBJECT-TYPE
	SYNTAX  SEQUENCE OF SnVLanByPortMemberEntry
	ACCESS  not-accessible
	STATUS  mandatory
	DESCRIPTION
		"Port VLAN (Layer 2 VLAN) port membership table."
	::= { snVLanInfo 6 }


snVLanByPortMemberEntry OBJECT-TYPE
	SYNTAX  SnVLanByPortMemberEntry
	ACCESS  not-accessible
	STATUS  mandatory
	DESCRIPTION
		"An entry of the port VLAN membership table."
	INDEX   { snVLanByPortMemberVLanId, snVLanByPortMemberPortId }
	::= { snVLanByPortMemberTable 1 }

SnVLanByPortMemberEntry ::= SEQUENCE {
	snVLanByPortMemberVLanId
		INTEGER,
	snVLanByPortMemberPortId
		INTEGER,
	snVLanByPortMemberRowStatus 
		INTEGER
	}

snVLanByPortMemberVLanId OBJECT-TYPE
	SYNTAX  INTEGER (1..4095)
	ACCESS  read-only
	STATUS  mandatory
	DESCRIPTION
		"The VLAN identifier (VLAN ID)."
	::= { snVLanByPortMemberEntry 1 }

snVLanByPortMemberPortId OBJECT-TYPE
	SYNTAX  INTEGER
	ACCESS  read-only
	STATUS  mandatory
	DESCRIPTION
		"The ifIndex which is a member of the port VLAN."
	::= { snVLanByPortMemberEntry 2 }

snVLanByPortMemberRowStatus OBJECT-TYPE
	SYNTAX  INTEGER {
		other(1),
		valid(2),
		delete(3),
		create(4)
		}
	ACCESS  read-write
	STATUS  mandatory
	DESCRIPTION
		"This object is used to create and
		delete row in the table and control
		if they are used. The values
		that can be written are:
		  delete(3)...deletes the row
		  create(4)...creates a new row

		If the row exists, then a SET with
		value of create(4) returns error
		'badValue'. Deleted rows go away
		immediately. The following values
		can be returned on reads:
		  noSuch(0)...no such row
		  other(1)....some other case
		  valid(2)....the row exists and is valid"
	::= { snVLanByPortMemberEntry 3 }


-- Port VLAN (Layer 2 VLAN) Configuration Table
-- Use this table to configure a VLAN entry


snVLanByPortCfgTable OBJECT-TYPE
	SYNTAX  SEQUENCE OF SnVLanByPortCfgEntry
	ACCESS  not-accessible
	STATUS  mandatory
	DESCRIPTION
		"Port VLAN (Layer 2 VLAN) configuration table."
	::= { snVLanInfo 7 }


snVLanByPortCfgEntry OBJECT-TYPE
	SYNTAX  SnVLanByPortCfgEntry
	ACCESS  not-accessible
	STATUS  mandatory
	DESCRIPTION
		"An entry of the port VLAN configuration table."
	INDEX   { snVLanByPortCfgVLanId }
	::= { snVLanByPortCfgTable 1 }


SnVLanByPortCfgEntry ::= SEQUENCE {
	snVLanByPortCfgVLanId
		INTEGER,
	snVLanByPortCfgQos
		INTEGER,
	snVLanByPortCfgStpMode
		INTEGER,
	snVLanByPortCfgStpPriority 
     	INTEGER,
	snVLanByPortCfgStpGroupMaxAge 
		INTEGER,
	snVLanByPortCfgStpGroupHelloTime 
		INTEGER,
	snVLanByPortCfgStpGroupForwardDelay 
		INTEGER,
	snVLanByPortCfgBaseNumPorts
    	INTEGER,
	snVLanByPortCfgBaseType
    	INTEGER, 
	snVLanByPortCfgStpProtocolSpecification 
     	INTEGER,
	snVLanByPortCfgStpMaxAge
     	Timeout,
	snVLanByPortCfgStpHelloTime 
     	Timeout,
	snVLanByPortCfgStpHoldTime 
     	INTEGER,
 	snVLanByPortCfgStpForwardDelay 
       	Timeout,
	snVLanByPortCfgStpTimeSinceTopologyChange 
     	TimeTicks,
	snVLanByPortCfgStpTopChanges
      	Counter,
	snVLanByPortCfgStpRootCost
    	INTEGER,
	snVLanByPortCfgStpRootPort
    	INTEGER,
	snVLanByPortCfgStpDesignatedRoot
     	BridgeId,
    snVLanByPortCfgBaseBridgeAddress 
        MacAddress,
	snVLanByPortCfgVLanName
		DisplayString,
    snVLanByPortCfgRouterIntf
	    INTEGER,
	snVLanByPortCfgRowStatus
		INTEGER,
	snVLanByPortCfgStpVersion
    	INTEGER
	}

snVLanByPortCfgVLanId OBJECT-TYPE
	SYNTAX  INTEGER (1..4095)
	ACCESS  read-only
	STATUS  mandatory
	DESCRIPTION
		"The VLAN identifier (VLAN ID)."
	::= { snVLanByPortCfgEntry 1 }

snVLanByPortCfgQos OBJECT-TYPE
	SYNTAX  INTEGER {
		level0(0),
		level1(1),
		level2(2),
		level3(3),
		level4(4),
		level5(5),
		level6(6),
		level7(7)
		}
	ACCESS  read-write
	STATUS  mandatory
	DESCRIPTION
		"The Stand alone stackable switch VLAN Priority values are:
		 level0(0)   -- low prority
		 level1(1) -- high prority.
		 The BigIron switch VLAN Priority values are:
		level0(0), level1(1), level2(2), level3(3),
		level4(4), level5(5), level6(6), level7(7) "
	::= { snVLanByPortCfgEntry 2 }

snVLanByPortCfgStpMode OBJECT-TYPE
	SYNTAX  INTEGER {
		disable(0),
		enableStp(1),
		enableRstp(2)
		}
	ACCESS  read-write
	STATUS  mandatory
	DESCRIPTION
		"Spanning Tree Mode in the Switch Group can be set
		 either enabled or disabled and the default is 
		 enabled mode.
		 disable(0)...........no Spanning Tree
		 enableStp(1).........activate Spanning Tree
		 enableRstp(2)........activate Rapid Spanning Tree"
	::= { snVLanByPortCfgEntry 3 }

snVLanByPortCfgStpPriority OBJECT-TYPE
    SYNTAX  INTEGER (0..65535)
    ACCESS  read-write
    STATUS  mandatory
    DESCRIPTION
	"dot1dStpPriority : The value of the write-able 
	 portion of the Stp ID, i.e., the first two octets 
	 of the (8 octet long) Bridge ID.  The other (last) 6 
	 octets of the Bridge ID are given by the value of the 
	 base bridge address - dot1dBaseBridgeAddress."
	::= { snVLanByPortCfgEntry 4 }

snVLanByPortCfgStpGroupMaxAge OBJECT-TYPE
    SYNTAX  INTEGER
    ACCESS  read-write
    STATUS  mandatory
    DESCRIPTION
    "dot1dStpBridgeMaxAge: From RFC1493(Bridge MIB).
     The value that all bridges use for MaxAge when 
     this bridge is acting as the root. 
     Note that 802.1D-1990 specifies that the 
     range for this parameter is related to the value of
     dot1dStpBridgeHelloTime. The granularity of this
     timer is specified by 802.1D-1990 to be 1 second.
     An agent may return a badValue error if a set is
     attempted to a value which is not a whole number
     of seconds.
       Valid value betweek 6 and 40. Default is 20 seconds.
     Value 0 is returned if no STP is not configured for this vlan."
        ::= { snVLanByPortCfgEntry 5 }

snVLanByPortCfgStpGroupHelloTime OBJECT-TYPE
    SYNTAX  INTEGER
    ACCESS  read-write
    STATUS  mandatory
    DESCRIPTION
    "dot1dStpBridgeHelloTime: From RFC1493(Bridge MIB).
     The value that all bridges use for HelloTime when
     this bridge is acting as the root.  The
     granularity of this timer is specified by 802.1D-
     1990 to be 1 second.  An agent may return a
     badValue error if a set is attempted to a value
     which is not a whole number of seconds.
       Valid value betweek 1 and 10. Default is 2 seconds.
     Value 0 is returned if no STP is not configured for this vlan."
	::= { snVLanByPortCfgEntry 6 }

snVLanByPortCfgStpGroupForwardDelay OBJECT-TYPE
	SYNTAX  INTEGER
    ACCESS  read-write
    STATUS  mandatory
    DESCRIPTION
	"dot1dStpBridgeForwardDelay : From RFC1493(Bridge MIB).
     The value that all bridges use for ForwardDelay
     when this bridge is acting as the root.  Note that
     802.1D-1990 specifies that the range for this
     parameter is related to the value of
     dot1dStpBridgeMaxAge.  The granularity of this
     timer is specified by 802.1D-1990 to be 1 second.
     An agent may return a badValue error if a set is
     attempted to a value which is not a whole number
     of seconds.
       Valid value betweek 2 and 30. Default is 15 seconds.
     Value 0 is returned if no STP is not configured for this vlan."
	::= { snVLanByPortCfgEntry 7 }

snVLanByPortCfgBaseNumPorts OBJECT-TYPE
    SYNTAX  INTEGER
    ACCESS  read-only
    STATUS  mandatory
    DESCRIPTION
    "The number of ports controlled by this bridging
     entity."
	::= { snVLanByPortCfgEntry 8 }

snVLanByPortCfgBaseType OBJECT-TYPE
    SYNTAX  INTEGER {
              unknown(1),
              transparent-only(2),
              sourceroute-only(3),
              srt(4)
            }
    ACCESS  read-only
    STATUS  mandatory
    DESCRIPTION
    "Indicates what type of bridging this bridge can
     perform.  If a bridge is actually performing a
     certain type of bridging this will be indicated by
     entries in the port table for the given type."
	::= { snVLanByPortCfgEntry 9 }

snVLanByPortCfgStpProtocolSpecification OBJECT-TYPE
    SYNTAX  INTEGER {
        unknown(1),
        decLb100(2),
        ieee8021d(3)
        }
    ACCESS  read-only
    STATUS  mandatory
    DESCRIPTION
    "An indication of what version of the Spanning
     Tree Protocol is being run.  The value
     'decLb100(2)' indicates the DEC LANbridge 100
     Spanning Tree protocol.  IEEE 802.1d
     implementations will return 'ieee8021d(3)'.  If
     future versions of the IEEE Spanning Tree Protocol
     are released that are incompatible with the
     current version a new value will be defined."
	::= { snVLanByPortCfgEntry 10 }


snVLanByPortCfgStpMaxAge OBJECT-TYPE
    SYNTAX  Timeout
    ACCESS  read-only
    STATUS  mandatory
    DESCRIPTION
    "dot1dStpMaxAge: From RFC1493(Bridge MIB).
     The maximum age of Spanning Tree Protocol
     information learned from the network on any port
     before it is discarded, in units of hundredths of
     a second.  This is the actual value that this
     bridge is currently using."
	::= { snVLanByPortCfgEntry 11 }

snVLanByPortCfgStpHelloTime OBJECT-TYPE
    SYNTAX  Timeout
    ACCESS  read-only
    STATUS  mandatory
    DESCRIPTION
    "dot1dStpHelloTime: From RFC1493(Bridge MIB).
     The amount of time between the transmission of
     Configuration bridge PDUs by this node on any port
     when it is the root of the spanning tree or trying
     to become so, in units of hundredths of a second.
     This is the actual value that this bridge is
     currently using."
	::= { snVLanByPortCfgEntry 12 }

snVLanByPortCfgStpHoldTime OBJECT-TYPE
    SYNTAX  INTEGER
    ACCESS  read-only
    STATUS  mandatory
    DESCRIPTION
    "dot1dStpHoldTime: From RFC1493(Bridge MIB).
     This time value determines the interval length
     during which no more than two Configuration bridge
     PDUs shall be transmitted by this node, in units
     of hundredths of a second."
	::= { snVLanByPortCfgEntry 13 }

 snVLanByPortCfgStpForwardDelay OBJECT-TYPE
     SYNTAX  Timeout
     ACCESS  read-only
     STATUS  mandatory
     DESCRIPTION
     "dot1dStpForwardDelay: From RFC1493(Bridge MIB).
      This time value, measured in units of hundredths
      of a second, controls how fast a port changes its
      spanning state when moving towards the Forwarding
      state.  The value determines how long the port
      stays in each of the Listening and Learning
      states, which precede the Forwarding state.  This
      value is also used, when a topology change has
      been detected and is underway, to age all dynamic
      entries in the Forwarding Database.  [Note that
      this value is the one that this bridge is
      currently using, in contrast to
      dot1dStpBridgeForwardDelay which is the value that
      this bridge and all others would start using
      if/when this bridge were to become the root.]"
	::= { snVLanByPortCfgEntry 14 }


snVLanByPortCfgStpTimeSinceTopologyChange OBJECT-TYPE
    SYNTAX  TimeTicks
    ACCESS  read-only
    STATUS  mandatory
    DESCRIPTION
    "The time (in hundredths of a second) since the
     last time a topology change was detected by the
     bridge entity."
	::= { snVLanByPortCfgEntry 15 }

snVLanByPortCfgStpTopChanges OBJECT-TYPE
    SYNTAX  Counter
    ACCESS  read-only
    STATUS  mandatory
    DESCRIPTION
    "The total number of topology changes detected by
     this bridge since the management entity was last
     reset or initialized."
	::= { snVLanByPortCfgEntry 16 }

snVLanByPortCfgStpRootCost OBJECT-TYPE
    SYNTAX  INTEGER
    ACCESS  read-only
    STATUS  mandatory
    DESCRIPTION
    "dot1dStpRootCost: From RFC1493(Bridge MIB).     
     The cost of the path to the root as seen from
     this bridge."
	::= { snVLanByPortCfgEntry 17 }

snVLanByPortCfgStpRootPort OBJECT-TYPE
    SYNTAX  INTEGER
    ACCESS  read-only
    STATUS  mandatory
    DESCRIPTION
    "dot1dStpRootPort: From RFC1493(Bridge MIB).
     The port number of the port which offers the
     lowest cost path from this bridge to the root
     bridge."
	::= { snVLanByPortCfgEntry 18 }

snVLanByPortCfgStpDesignatedRoot OBJECT-TYPE
    SYNTAX  BridgeId
    ACCESS  read-only
    STATUS  mandatory
    DESCRIPTION
    "dot1dStpDesignatedRoot: From RFC1493(Bridge MIB).
     The bridge identifier of the root of the spanning
     tree as determined by the Spanning Tree Protocol
     as executed by this node.  This value is used as
     the Root Identifier parameter in all Configuration
     Bridge PDUs originated by this node."
	::= { snVLanByPortCfgEntry 19 }

snVLanByPortCfgBaseBridgeAddress OBJECT-TYPE
    SYNTAX  MacAddress
    ACCESS  read-only
    STATUS  mandatory
    DESCRIPTION
    "The MAC address used by this bridge when it must
     be referred to in a unique fashion.   It is
     recommended that this be the numerically smallest
     MAC address of all ports that belong to this
     bridge.  However it is only required to be unique.
     When concatenated with dot1dStpPriority a unique
     BridgeIdentifier is formed which is used in the
     Spanning Tree Protocol."
	::= { snVLanByPortCfgEntry 20 }

snVLanByPortCfgVLanName OBJECT-TYPE
	SYNTAX	DisplayString (SIZE(0..32))
	ACCESS	read-write
	STATUS	mandatory
	DESCRIPTION
		"VLAN Community Name string."
	::= { snVLanByPortCfgEntry 21 }


snVLanByPortCfgRouterIntf OBJECT-TYPE
	SYNTAX  INTEGER
	ACCESS  read-write
	STATUS  mandatory
	DESCRIPTION
		"Optional: A virtual interface for router to the VLAN -- applied to router only.
		 If a SNMP-Get value is zero, that means this object was not configured."
	::= { snVLanByPortCfgEntry 22 }

snVLanByPortCfgRowStatus OBJECT-TYPE
	SYNTAX  INTEGER {
		other(1),
		valid(2),
		delete(3)
		}
	ACCESS  read-write
	STATUS  mandatory
	DESCRIPTION
		"Use object to delete a vlan entry."
	::= { snVLanByPortCfgEntry 23 }

snVLanByPortCfgStpVersion OBJECT-TYPE
	SYNTAX  INTEGER {
		stpCompatible(0),
		rstp(2)
		}
    ACCESS  read-write
    STATUS  mandatory
    DESCRIPTION
        "The version of Spanning Tree Protocol the bridge is
         currently running.  The value 'stpCompatible(0)'
         indicates the Spanning Tree Protocol specified in
         IEEE 802.1D and 'rstp(2)' indicates the Rapid Spanning
         Tree Protocol specified in IEEE 802.1w.  New value may
         be defined as future versions of the protocol become
         available."
	::= { snVLanByPortCfgEntry 24 }


-- VLAN by Protocol Configuration Table 


snVLanByProtocolTable OBJECT-TYPE
	SYNTAX  SEQUENCE OF SnVLanByProtocolEntry
	ACCESS  not-accessible
	STATUS  mandatory
	DESCRIPTION
		"."
	::= { snVLanInfo 2 }


snVLanByProtocolEntry OBJECT-TYPE
	SYNTAX  SnVLanByProtocolEntry
	ACCESS  not-accessible
	STATUS  mandatory
	DESCRIPTION
		"An entry in the VLAN By Protocol Configuration table. "
	INDEX   { 
		snVLanByProtocolVLanId,
	 	snVLanByProtocolIndex
	}
	::= { snVLanByProtocolTable 1 }


SnVLanByProtocolEntry ::= SEQUENCE {
    snVLanByProtocolVLanId
		INTEGER,
	snVLanByProtocolIndex
		INTEGER,
	snVLanByProtocolDynamic
  		INTEGER,
	snVLanByProtocolStaticMask
		PortMask,
	snVLanByProtocolExcludeMask
		PortMask,
	snVLanByProtocolRouterIntf
		INTEGER,	
	snVLanByProtocolRowStatus
		INTEGER,	
	snVLanByProtocolDynamicMask
		PortMask,
	snVLanByProtocolChassisStaticMask
		OCTET STRING,
	snVLanByProtocolChassisExcludeMask
		OCTET STRING,
	snVLanByProtocolChassisDynamicMask
		OCTET STRING,
	snVLanByProtocolVLanName
		DisplayString,
	snVLanByProtocolStaticPortList
		OCTET STRING,
	snVLanByProtocolExcludePortList
		OCTET STRING,
	snVLanByProtocolDynamicPortList
		OCTET STRING
	}

snVLanByProtocolVLanId OBJECT-TYPE
	SYNTAX  INTEGER (1..4095)
	ACCESS  read-only
	STATUS  mandatory
	DESCRIPTION
		"The VLAN ID index to both of the VLAN By Port Info Table
		 and this table."
	::= { snVLanByProtocolEntry 1 }


snVLanByProtocolIndex OBJECT-TYPE
	SYNTAX  INTEGER {
		ip(1),
	    ipx(2),
	    appleTalk(3),
	    decNet(4),
	    netBios(5),
		others(6),
		ipv6(7)
		}
	ACCESS  read-only
	STATUS  mandatory
	DESCRIPTION
		" The following IP/IPX protocol VLAN types are operated 
		in Layer3 VLAN such as : ip(1), ipx(2), ipv6(7)
		The following are operated in Layer2 bridging such as:
	    appleTalk(3), decNet(4), netBios(5),
	    others(6) -- other protocols which are defined here. "
	::= { snVLanByProtocolEntry 2 }

snVLanByProtocolDynamic OBJECT-TYPE
	SYNTAX  INTEGER {
		disabled(0),
	    enabled(1)
		}
	ACCESS  read-write
	STATUS  mandatory
	DESCRIPTION
		" disabled(0) : disabled dynamic port inclusion - applied to switch only.
		  enabled(1) : enabled dynamic port inclusion - applied to switch only. "
	::= { snVLanByProtocolEntry 3 }

snVLanByProtocolStaticMask OBJECT-TYPE
	SYNTAX  PortMask
	ACCESS  read-write
	STATUS  deprecated
	DESCRIPTION
		"The Standand-alone switch Protocol VLAN port membership applied in static mode.
		(It was obsoleted for Chassis Product)"
	::= { snVLanByProtocolEntry 4 }

snVLanByProtocolExcludeMask OBJECT-TYPE
	SYNTAX  PortMask
	ACCESS  read-write
	STATUS  deprecated
	DESCRIPTION
		"The Standand-alone switch Protocol VLAN port membership applied in exclusive mode.
		(It was obsoleted for Chassis Product)"
	::= { snVLanByProtocolEntry 5 }

snVLanByProtocolRouterIntf OBJECT-TYPE
	SYNTAX  INTEGER (1..60)
	ACCESS  read-write
	STATUS  mandatory
	DESCRIPTION
		"Optional: A virtual interface for router to the VLAN -- applied to router only.
		 If a SNMP-Get value is zero, that means this object was not configured."
	::= { snVLanByProtocolEntry 6 }

snVLanByProtocolRowStatus OBJECT-TYPE
	SYNTAX  INTEGER {
		other(1),
		valid(2),
		delete(3),
		create(4),
		modify(5)
		}
	ACCESS  read-write
	STATUS  mandatory
	DESCRIPTION
		"This object is used to create and
		delete row in the table and control
		if they are used. The values
		that can be written are:
		  delete(3)...deletes the row
		  create(4)...creates a new row
		  modify(5)...modifies an exsisting row

		If the row exists, then a SET with
		value of create(4) returns error
		'badValue'. Deleted rows go away
		immediately. The following values
		can be returned on reads:
		  noSuch(0)...no such row
		  other(1)....some other case
		  valid(2)....the row exists and is valid"
	::= { snVLanByProtocolEntry 7 }

snVLanByProtocolDynamicMask OBJECT-TYPE
	SYNTAX  PortMask
	ACCESS  read-only
	STATUS  deprecated
	DESCRIPTION
		"The Standand-alone switch Protocol VLAN active port membership.
		(It was obsoleted for Chassis Product)"
	::= { snVLanByProtocolEntry 8 }

snVLanByProtocolChassisStaticMask OBJECT-TYPE
	SYNTAX  OCTET STRING (SIZE(32))
	ACCESS  read-write
	STATUS  deprecated
	DESCRIPTION
		"The Chassis Protocol VLAN port membership applied in static mode.
		(It was obsoleted after release 07100, replaced by snVLanByProtocolStaticPortList)"
	::= { snVLanByProtocolEntry 9 }

snVLanByProtocolChassisExcludeMask OBJECT-TYPE
	SYNTAX  OCTET STRING (SIZE(32))
	ACCESS  read-write
	STATUS  deprecated
	DESCRIPTION
		"The Chassis Protocol VLAN port membership applied in exclusive mode.
		(It was obsoleted after release 07100, replaced by snVLanByProtocolExcludePortList)"
	::= { snVLanByProtocolEntry 10 }

snVLanByProtocolChassisDynamicMask OBJECT-TYPE
	SYNTAX  OCTET STRING (SIZE(32))
	ACCESS  read-only
	STATUS  deprecated
	DESCRIPTION
		"The Chassis Protocol VLAN active port membership.
		(It was obsoleted after release 07100, replaced by snVLanByProtocolDynamicPortList)"
	::= { snVLanByProtocolEntry 11 }

snVLanByProtocolVLanName OBJECT-TYPE
	SYNTAX	DisplayString (SIZE(0..32))
	ACCESS	read-write
	STATUS	mandatory
	DESCRIPTION
		"VLAN Community Name string."
	::= { snVLanByProtocolEntry 12 }

snVLanByProtocolStaticPortList OBJECT-TYPE
	SYNTAX  OCTET STRING
	ACCESS  read-write
	STATUS  mandatory
	DESCRIPTION
		"A list of port indices which are the configured port
		membership of the Protocol VLAN. Each port index is a
		16-bit integer in big endian order. 8-bit is the slot number,
		the other 8-bit is the port number."
	::= { snVLanByProtocolEntry 13 }

snVLanByProtocolExcludePortList OBJECT-TYPE
	SYNTAX  OCTET STRING
	ACCESS  read-write
	STATUS  mandatory
	DESCRIPTION
		"A list of port indices which are the excluded from port
		membership of the Protocol VLAN. Each port index is a
		16-bit integer in big endian order. 8-bit is the slot number,
		the other 8-bit is the port number."
	::= { snVLanByProtocolEntry 14 }

snVLanByProtocolDynamicPortList OBJECT-TYPE
	SYNTAX  OCTET STRING
	ACCESS  read-only
	STATUS  mandatory
	DESCRIPTION
		"A list of port indices which are dynamically joining the port
		membership of the Protocol VLAN. Each port index is a
		16-bit integer in big endian order. 8-bit is the slot number,
		the other 8-bit is the port number."
	::= { snVLanByProtocolEntry 15 }


-- VLAN By IP Subnet Configuration Table


snVLanByIpSubnetTable OBJECT-TYPE
	SYNTAX  SEQUENCE OF SnVLanByIpSubnetEntry
	ACCESS  not-accessible
	STATUS  mandatory
	DESCRIPTION
		"An entry of the VLAN By IPX Network Number Table."
	::= { snVLanInfo 3 }


snVLanByIpSubnetEntry OBJECT-TYPE
	SYNTAX  SnVLanByIpSubnetEntry
	ACCESS  not-accessible
	STATUS  mandatory
	DESCRIPTION
		"An entry in the VLAN By IP Subnet Configuration table. "
	INDEX   { 
		snVLanByIpSubnetVLanId,
		snVLanByIpSubnetIpAddress,
		snVLanByIpSubnetSubnetMask
	}
	::= { snVLanByIpSubnetTable 1 }


SnVLanByIpSubnetEntry ::= SEQUENCE {
	snVLanByIpSubnetVLanId
		INTEGER,
	snVLanByIpSubnetIpAddress
		IpAddress,
	snVLanByIpSubnetSubnetMask
		IpAddress,
	snVLanByIpSubnetDynamic
  		INTEGER,
	snVLanByIpSubnetStaticMask
		PortMask,
	snVLanByIpSubnetExcludeMask
		PortMask,
	snVLanByIpSubnetRouterIntf
		INTEGER,
	snVLanByIpSubnetRowStatus
		INTEGER,
	snVLanByIpSubnetDynamicMask
		PortMask,
	snVLanByIpSubnetChassisStaticMask
		OCTET STRING,
	snVLanByIpSubnetChassisExcludeMask
		OCTET STRING,
	snVLanByIpSubnetChassisDynamicMask
		OCTET STRING,
	snVLanByIpSubnetVLanName
		DisplayString,
	snVLanByIpSubnetStaticPortList
		OCTET STRING,
	snVLanByIpSubnetExcludePortList
		OCTET STRING,
	snVLanByIpSubnetDynamicPortList
		OCTET STRING
	}

snVLanByIpSubnetVLanId OBJECT-TYPE
	SYNTAX  INTEGER (1..4095)
	ACCESS  read-only
	STATUS  mandatory
	DESCRIPTION
		"The VLAN ID index to both of the VLAN By Port Info Table
		 and this table."
	::= { snVLanByIpSubnetEntry 1 }


snVLanByIpSubnetIpAddress OBJECT-TYPE
	SYNTAX  IpAddress
	ACCESS  read-only
	STATUS  mandatory
	DESCRIPTION
		"Subnet IP address."
	::= { snVLanByIpSubnetEntry 2 }

snVLanByIpSubnetSubnetMask OBJECT-TYPE
	SYNTAX  IpAddress
	ACCESS  read-only
	STATUS  mandatory
	DESCRIPTION
		"Subnet mask associated with the Subnet IP address."
	::= { snVLanByIpSubnetEntry 3 }

snVLanByIpSubnetDynamic OBJECT-TYPE
	SYNTAX  INTEGER {
		disabled(0),
	    enabled(1)
		}
	ACCESS  read-write
	STATUS  mandatory
	DESCRIPTION
		" disabled(0) : disabled dynamic port inclusion - applied to switch only.
		  enabled(1) : enabled dynamic port inclusion - applied to switch only. "
	::= { snVLanByIpSubnetEntry 4 }

snVLanByIpSubnetStaticMask OBJECT-TYPE
	SYNTAX  PortMask
	ACCESS  read-write
	STATUS  deprecated
	DESCRIPTION
		"The Standand-alone switch VLAN By Subnet port membership applied in static mode.
		(It was obsoleted for Chassis Product)"
	::= { snVLanByIpSubnetEntry 5 }

snVLanByIpSubnetExcludeMask OBJECT-TYPE
	SYNTAX  PortMask
	ACCESS  read-write
	STATUS  deprecated
	DESCRIPTION
		"The Standand-alone switch VLAN By Subnet port membership applied in exclusive mode.
		(It was obsoleted for Chassis Product)"
	::= { snVLanByIpSubnetEntry 6 }

snVLanByIpSubnetRouterIntf OBJECT-TYPE
	SYNTAX  INTEGER (1..60)
	ACCESS  read-write
	STATUS  mandatory
	DESCRIPTION
		"Optional: A virtual interface for router to the VLAN -- applied to router only.
		 If a SNMP-Get value is zero, that means this object was not configured."
	::= { snVLanByIpSubnetEntry 7 }


snVLanByIpSubnetRowStatus OBJECT-TYPE
	SYNTAX  INTEGER {
		other(1),
		valid(2),
		delete(3),
		create(4),
		modify(5)
		}
	ACCESS  read-write
	STATUS  mandatory
	DESCRIPTION
		"This object is used to create and
		delete row in the table and control
		if they are used. The values
		that can be written are:
		  delete(3)...deletes the row
		  create(4)...creates a new row
		  modify(5)...modifies an exsisting row

		If the row exists, then a SET with
		value of create(4) returns error
		'badValue'. Deleted rows go away
		immediately. The following values
		can be returned on reads:
		  noSuch(0)...no such row
		  other(1)....some other case
		  valid(2)....the row exists and is valid"
	::= { snVLanByIpSubnetEntry 8 }

snVLanByIpSubnetDynamicMask OBJECT-TYPE
	SYNTAX  PortMask
	ACCESS  read-only
	STATUS  deprecated
	DESCRIPTION
		"The Standand-alone switch VLAN By Subnet active port membership.
		(It was obsoleted for Chassis Product)"
	::= { snVLanByIpSubnetEntry 9 }

snVLanByIpSubnetChassisStaticMask OBJECT-TYPE
	SYNTAX  OCTET STRING (SIZE(32))
	ACCESS  read-write
	STATUS  deprecated
	DESCRIPTION
		"The Chassis VLAN By Subnet port membership applied in static mode.
		(It was obsoleted after release 07100, replaced by snVLanByIpSubnetStaticPortList)"
	::= { snVLanByIpSubnetEntry 10 }

snVLanByIpSubnetChassisExcludeMask OBJECT-TYPE
	SYNTAX  OCTET STRING (SIZE(32))
	ACCESS  read-write
	STATUS  deprecated
	DESCRIPTION
		"The Chassis VLAN By Subnet port membership applied in exclusive mode.
		(It was obsoleted after release 07100, replaced by snVLanByIpSubnetExcludePortList)"
	::= { snVLanByIpSubnetEntry 11 }

snVLanByIpSubnetChassisDynamicMask OBJECT-TYPE
	SYNTAX  OCTET STRING (SIZE(32))
	ACCESS  read-only
	STATUS  deprecated
	DESCRIPTION
		"The Chassis VLAN By Subnet active port membership.
		(It was obsoleted after release 07100, replaced by snVLanByIpSubnetDynamicPortList)"
	::= { snVLanByIpSubnetEntry 12 }

snVLanByIpSubnetVLanName OBJECT-TYPE
	SYNTAX	DisplayString (SIZE(0..32))
	ACCESS	read-write
	STATUS	mandatory
	DESCRIPTION
		"VLAN Community Name string."
	::= { snVLanByIpSubnetEntry 13 }

snVLanByIpSubnetStaticPortList OBJECT-TYPE
	SYNTAX  OCTET STRING
	ACCESS  read-write
	STATUS  mandatory
	DESCRIPTION
		"A list of port indices which are the configured port
		membership of the VLAN By IP Subnet. Each port index is a
		16-bit integer in big endian order. 8-bit is the slot number,
		the other 8-bit is the port number."
	::= { snVLanByIpSubnetEntry 14 }

snVLanByIpSubnetExcludePortList OBJECT-TYPE
	SYNTAX  OCTET STRING
	ACCESS  read-write
	STATUS  mandatory
	DESCRIPTION
		"A list of port indices which are the excluded from port
		membership of the VLAN By IP Subnet. Each port index is a
		16-bit integer in big endian order. 8-bit is the slot number,
		the other 8-bit is the port number."
	::= { snVLanByIpSubnetEntry 15 }

snVLanByIpSubnetDynamicPortList OBJECT-TYPE
	SYNTAX  OCTET STRING
	ACCESS  read-only
	STATUS  mandatory
	DESCRIPTION
		"A list of port indices which are dynamically joining the port
		membership of the VLAN By IP Subnet. Each port index is a
		16-bit integer in big endian order. 8-bit is the slot number,
		the other 8-bit is the port number."
	::= { snVLanByIpSubnetEntry 16 }


-- VLAN By IPX Net Configuration Table


snVLanByIpxNetTable OBJECT-TYPE
	SYNTAX  SEQUENCE OF SnVLanByIpxNetEntry
	ACCESS  not-accessible
	STATUS  mandatory
	DESCRIPTION
		"An entry of the VLAN By IPX Network Number Table."
	::= { snVLanInfo 4 }


snVLanByIpxNetEntry OBJECT-TYPE
	SYNTAX  SnVLanByIpxNetEntry
	ACCESS  not-accessible
	STATUS  mandatory
	DESCRIPTION
		"An entry in the VLAN By Ipx Network Number Configuration table. "
	INDEX   { 
		snVLanByIpxNetVLanId,
		snVLanByIpxNetNetworkNum,
		snVLanByIpxNetFrameType
	}
	::= { snVLanByIpxNetTable 1 }


SnVLanByIpxNetEntry ::= SEQUENCE {
	snVLanByIpxNetVLanId
		INTEGER,
	snVLanByIpxNetNetworkNum
		OCTET STRING,
	snVLanByIpxNetFrameType
  		INTEGER,
	snVLanByIpxNetDynamic
  		INTEGER,
	snVLanByIpxNetStaticMask
		PortMask,
	snVLanByIpxNetExcludeMask
		PortMask,
	snVLanByIpxNetRouterIntf
		INTEGER,
	snVLanByIpxNetRowStatus
		INTEGER,
	snVLanByIpxNetDynamicMask
		PortMask,
	snVLanByIpxNetChassisStaticMask
		OCTET STRING,
	snVLanByIpxNetChassisExcludeMask
		OCTET STRING,
	snVLanByIpxNetChassisDynamicMask
		OCTET STRING,
	snVLanByIpxNetVLanName
		DisplayString,
	snVLanByIpxNetStaticPortList
		OCTET STRING,
	snVLanByIpxNetExcludePortList
		OCTET STRING,
	snVLanByIpxNetDynamicPortList
		OCTET STRING
	}

snVLanByIpxNetVLanId OBJECT-TYPE
	SYNTAX  INTEGER (1..4095)
	ACCESS  read-only
	STATUS  mandatory
	DESCRIPTION
		"The VLAN ID index to both of the VLAN By Port Info Table
		 and this table."
	::= { snVLanByIpxNetEntry 1 }


snVLanByIpxNetNetworkNum OBJECT-TYPE
	SYNTAX  OCTET STRING (SIZE(4))
	ACCESS  read-only
	STATUS  mandatory
	DESCRIPTION
		"IPX Network Number."
	::= { snVLanByIpxNetEntry 2 }

snVLanByIpxNetFrameType OBJECT-TYPE
	SYNTAX  INTEGER {
	    notApplicable(0),
		ipxEthernet8022(1),
	    ipxEthernet8023(2),
	    ipxEthernetII(3),
	    ipxEthernetSnap(4)
		}
	ACCESS  read-only
	STATUS  mandatory
	DESCRIPTION
		" The following IPX Frame types are operated 
		in Layer3 VLAN such as :  
		ipxEthernet8022(1), ipxEthernet8023(2),
	    ipxEthernetII(3), ipxEthernetSnap(4).
	    choose notApplicable(0) for other protocols.
	    Note: Each Network Number can be assigned with one unique Frame type; Otherwise,
	    a SNMP-SET error will be returned."
	::= { snVLanByIpxNetEntry 3 }

snVLanByIpxNetDynamic OBJECT-TYPE
	SYNTAX  INTEGER {
		disabled(0),
	    enabled(1)
		}
	ACCESS  read-write
	STATUS  mandatory
	DESCRIPTION
		" disabled(0) : disabled dynamic port inclusion - applied to switch only.
		  enabled(1) : enabled dynamic port inclusion - applied to switch only. "
	::= { snVLanByIpxNetEntry 4 }

snVLanByIpxNetStaticMask OBJECT-TYPE
	SYNTAX  PortMask
	ACCESS  read-write
	STATUS  deprecated
	DESCRIPTION
		"The VLAN By IPX network port membership applied in static mode.
		(It was obsoleted for Chassis Product)"
	::= { snVLanByIpxNetEntry 5 }

snVLanByIpxNetExcludeMask OBJECT-TYPE
	SYNTAX  PortMask
	ACCESS  read-write
	STATUS  deprecated
	DESCRIPTION
		"The VLAN By IPX network port membership applied in exclusive mode.
		(It was obsoleted for Chassis Product)"
	::= { snVLanByIpxNetEntry 6 }


snVLanByIpxNetRouterIntf OBJECT-TYPE
	SYNTAX  INTEGER (1..60)
	ACCESS  read-write
	STATUS  mandatory
	DESCRIPTION
		"Optional: A virtual interface for router to the VLAN -- applied to router only.
		 If a SNMP-Get value is zero, that means this object was not configured."
	::= { snVLanByIpxNetEntry 7 }


snVLanByIpxNetRowStatus OBJECT-TYPE
	SYNTAX  INTEGER {
		other(1),
		valid(2),
		delete(3),
		create(4),
		modify(5)
		}
	ACCESS  read-write
	STATUS  mandatory
	DESCRIPTION
		"This object is used to create and
		delete row in the table and control
		if they are used. The values
		that can be written are:
		  delete(3)...deletes the row
		  create(4)...creates a new row
		  modify(5)...modifies an exsisting row

		If the row exists, then a SET with
		value of create(4) returns error
		'badValue'. Deleted rows go away
		immediately. The following values
		can be returned on reads:
		  noSuch(0)...no such row
		  other(1)....some other case
		  valid(2)....the row exists and is valid"
	::= { snVLanByIpxNetEntry 8 }

snVLanByIpxNetDynamicMask OBJECT-TYPE
	SYNTAX  PortMask
	ACCESS  read-only
	STATUS  deprecated
	DESCRIPTION
		"The VLAN By IPX network active port membership.
		(It was obsoleted for Chassis Product)"
	::= { snVLanByIpxNetEntry 9 }

snVLanByIpxNetChassisStaticMask OBJECT-TYPE
	SYNTAX  OCTET STRING (SIZE(32))
	ACCESS  read-write
	STATUS  deprecated
	DESCRIPTION
		"The Chassis VLAN By IPX network port membership applied in static mode.
		(It was obsoleted after release 07100, replaced by snVLanByIpxNetStaticPortList)"
	::= { snVLanByIpxNetEntry 10 }

snVLanByIpxNetChassisExcludeMask OBJECT-TYPE
	SYNTAX  OCTET STRING (SIZE(32))
	ACCESS  read-write
	STATUS  deprecated
	DESCRIPTION
		"The Chassis VLAN By IPX network port membership applied in exclusive mode.
		(It was obsoleted after release 07100, replaced by snVLanByIpxNetExcludePortList)"
	::= { snVLanByIpxNetEntry 11 }

snVLanByIpxNetChassisDynamicMask OBJECT-TYPE
	SYNTAX  OCTET STRING (SIZE(32))
	ACCESS  read-only
	STATUS  deprecated
	DESCRIPTION
		"The Chassis VLAN By IPX network active port membership.
		(It was obsoleted after release 07100, replaced by snVLanByIpxNetDynamicPortList)"
	::= { snVLanByIpxNetEntry 12 }

snVLanByIpxNetVLanName OBJECT-TYPE
	SYNTAX	DisplayString (SIZE(0..32))
	ACCESS	read-write
	STATUS	mandatory
	DESCRIPTION
		"VLAN Community Name string."
	::= { snVLanByIpxNetEntry 13 }

snVLanByIpxNetStaticPortList OBJECT-TYPE
	SYNTAX  OCTET STRING
	ACCESS  read-write
	STATUS  mandatory
	DESCRIPTION
		"A list of port indices which are the configured port
		membership of the VLAN By IPX network. Each port index is a
		16-bit integer in big endian order. 8-bit is the slot number,
		the other 8-bit is the port number."
	::= { snVLanByIpxNetEntry 14 }

snVLanByIpxNetExcludePortList OBJECT-TYPE
	SYNTAX  OCTET STRING
	ACCESS  read-write
	STATUS  mandatory
	DESCRIPTION
		"A list of port indices which are the excluded from port
		membership of the VLAN By IPX network. Each port index is a
		16-bit integer in big endian order. 8-bit is the slot number,
		the other 8-bit is the port number."
	::= { snVLanByIpxNetEntry 15 }

snVLanByIpxNetDynamicPortList OBJECT-TYPE
	SYNTAX  OCTET STRING
	ACCESS  read-only
	STATUS  mandatory
	DESCRIPTION
		"A list of port indices which are dynamically joining the port
		membership of the VLAN By IPX network. Each port index is a
		16-bit integer in big endian order. 8-bit is the slot number,
		the other 8-bit is the port number."
	::= { snVLanByIpxNetEntry 16 }


-- VLAN By AppleTalk Cable Configuration Table


snVLanByATCableTable OBJECT-TYPE
	SYNTAX  SEQUENCE OF SnVLanByATCableEntry
	ACCESS  not-accessible
	STATUS  mandatory
	DESCRIPTION
		"A Table Of VLAN By AppleTalk Network Number."
	::= { snVLanInfo 5 }

snVLanByATCableEntry OBJECT-TYPE
	SYNTAX  SnVLanByATCableEntry
	ACCESS  not-accessible
	STATUS  mandatory
	DESCRIPTION
		"An entry of the AppleTalk Cable VLAN table."
	INDEX   {snVLanByATCableVLanId, snVLanByATCableIndex}
	::= { snVLanByATCableTable 1 }

SnVLanByATCableEntry ::= SEQUENCE {
	snVLanByATCableVLanId
		INTEGER,
	snVLanByATCableIndex
		INTEGER,
	snVLanByATCableRouterIntf
		INTEGER,
	snVLanByATCableRowStatus
		INTEGER,
	snVLanByATCableChassisStaticMask
		OCTET STRING,
	snVLanByATCableVLanName
		DisplayString,
	snVLanByATCableStaticPortList
		OCTET STRING
	}

snVLanByATCableVLanId OBJECT-TYPE
	SYNTAX  INTEGER (1..4095)
	ACCESS  read-only
	STATUS  mandatory
	DESCRIPTION
		"The VLAN ID of a PORT VLAN of which the AppleTalk Cable
		VLAN was attaching to."
	::= { snVLanByATCableEntry 1 }

snVLanByATCableIndex OBJECT-TYPE
	SYNTAX  INTEGER
	ACCESS  read-only
	STATUS  mandatory
	DESCRIPTION
		"AppleTalk Cable VLAN index number."
	::= { snVLanByATCableEntry 2 }

snVLanByATCableRouterIntf OBJECT-TYPE
	SYNTAX  INTEGER (0..60)
	ACCESS  read-write
	STATUS  mandatory
	DESCRIPTION
		"A virtual router interface to the AppleTalk Cable VLAN,
		only router products accept the SNMP-SET operation. The
		value zero indicates that virtual router interface was
		not configured."
	::= { snVLanByATCableEntry 3 }

snVLanByATCableRowStatus OBJECT-TYPE
	SYNTAX  INTEGER {
		other(1),
		valid(2),
		delete(3),
		create(4),
		modify(5)
		}
	ACCESS  read-write
	STATUS  mandatory
	DESCRIPTION
		"This object is used to create and
		delete row in the table and control
		if they are used. The values
		that can be written are:
		  delete(3)...deletes the row
		  create(4)...creates a new row
		  modify(5)...modifies an exsisting row

		If the row exists, then a SET with
		value of create(4) returns error
		'badValue'. Deleted rows go away
		immediately. The following values
		can be returned on reads:
		  noSuch(0)...no such row
		  other(1)....some other case
		  valid(2)....the row exists and is valid"
	::= { snVLanByATCableEntry 4 }

snVLanByATCableChassisStaticMask OBJECT-TYPE
	SYNTAX  OCTET STRING (SIZE(32))
	ACCESS  read-write
	STATUS  deprecated
	DESCRIPTION
		"A list of ports which are statically configured to
		become port members of a VLAN.
		(It was obsoleted after release 07100, replaced by snVLanByATCableStaticPortList)"
	::= { snVLanByATCableEntry 5 }

snVLanByATCableVLanName OBJECT-TYPE
	SYNTAX	DisplayString (SIZE(0..32))
	ACCESS	read-write
	STATUS	mandatory
	DESCRIPTION
		"VLAN Name string."
	::= { snVLanByATCableEntry 6 }

snVLanByATCableStaticPortList OBJECT-TYPE
	SYNTAX  OCTET STRING
	ACCESS  read-write
	STATUS  mandatory
	DESCRIPTION
		"A list of port indices which are the configured port
		membership of the AppleTalk Cable VLAN. Each port index is a
		16-bit integer in big endian order. 8-bit is the slot number,
		the other 8-bit is the port number."
	::= { snVLanByATCableEntry 7 }




-- Switch Port Information Group

-- begin of deprecated snSwPortInfoTable
snSwPortInfoTable OBJECT-TYPE
	SYNTAX  SEQUENCE OF SnSwPortInfoEntry
	ACCESS  not-accessible
	STATUS  deprecated
	DESCRIPTION
		"A specific snSwPortInfo group consists of a number of 
		 switch ports.  "
	::= { snSwPortInfo 1 }

snSwPortInfoEntry OBJECT-TYPE
	SYNTAX  SnSwPortInfoEntry
	ACCESS  not-accessible
	STATUS  deprecated
	DESCRIPTION
		"An entry in the snSwPortInfo table indicates the 
		 configuration on a specified port. A SNMP SET PDU 
		 for a row of the snSwPortInfoTable requires the entired 
		 sequence of the MIB Objects in each 
		 snSwPortInfoEntry stored in one PDU.  Otherwise, 
	 	 GENERR return-value will be returned."
	INDEX   { 
		snSwPortInfoPortNum
	}
	::= { snSwPortInfoTable 1 }

SnSwPortInfoEntry ::= SEQUENCE {
	snSwPortInfoPortNum
		INTEGER,
	snSwPortInfoMonitorMode
	    INTEGER,
	snSwPortInfoTagMode
		INTEGER,
	snSwPortInfoChnMode
	    INTEGER,
	snSwPortInfoSpeed
	    INTEGER,
    snSwPortInfoMediaType
	    INTEGER,
	snSwPortInfoConnectorType
	    INTEGER,
	snSwPortInfoAdminStatus
		INTEGER,
	snSwPortInfoLinkStatus
		INTEGER,
	snSwPortInfoPortQos
	    INTEGER,
	snSwPortInfoPhysAddress
	    PhysAddress,
    snSwPortStatsInFrames 
    	Counter,
	snSwPortStatsOutFrames 
    	Counter,
	snSwPortStatsAlignErrors            
		Counter,
    snSwPortStatsFCSErrors                  
		Counter,
    snSwPortStatsMultiColliFrames    
		Counter,
    snSwPortStatsFrameTooLongs              
		Counter,
	snSwPortStatsTxColliFrames
	    Counter,
	snSwPortStatsRxColliFrames
	    Counter,
	snSwPortStatsFrameTooShorts
	    Counter,
	snSwPortLockAddressCount
	    INTEGER,
	snSwPortStpPortEnable
	    INTEGER,
    snSwPortDhcpGateListId
	    INTEGER,
	snSwPortName
		DisplayString,
	snSwPortStatsInBcastFrames
	    Counter,
	snSwPortStatsOutBcastFrames
	    Counter,
	snSwPortStatsInMcastFrames
	    Counter,
	snSwPortStatsOutMcastFrames
	    Counter,
	snSwPortStatsInDiscard
	    Counter,
	snSwPortStatsOutDiscard
	    Counter,
	snSwPortStatsMacStations
	    INTEGER,
	snSwPortCacheGroupId
	    INTEGER,
	snSwPortTransGroupId
	    INTEGER,
	snSwPortInfoAutoNegotiate
	    INTEGER,
	snSwPortInfoFlowControl
	    INTEGER,
	snSwPortInfoGigType
	    INTEGER,
	snSwPortStatsLinkChange
	    Counter,
	snSwPortIfIndex
	    INTEGER,
	snSwPortDescr
	    DisplayString,
	snSwPortInOctets
	    OCTET STRING,
	snSwPortOutOctets
	    OCTET STRING,
	snSwPortStatsInBitsPerSec
	    Gauge,
	snSwPortStatsOutBitsPerSec
	    Gauge,
	snSwPortStatsInPktsPerSec
	    Gauge,
	snSwPortStatsOutPktsPerSec
	    Gauge,
	snSwPortStatsInUtilization
	    INTEGER (0..10000),
	snSwPortStatsOutUtilization
	    INTEGER (0..10000),
	snSwPortFastSpanPortEnable
	    INTEGER,
	snSwPortFastSpanUplinkEnable
	    INTEGER,
	snSwPortVlanId
	    INTEGER,
	snSwPortRouteOnly
	    INTEGER,
	snSwPortPresent
	    INTEGER,
	snSwPortGBICStatus
	    INTEGER,
	snSwPortStatsInKiloBitsPerSec
		Unsigned32,
	snSwPortStatsOutKiloBitsPerSec    
		Unsigned32,
	snSwPortLoadInterval
	    INTEGER (30..300),
	snSwPortTagType
	    INTEGER,
	snSwPortInLinePowerControl
	    INTEGER,
	snSwPortInLinePowerWattage
	    INTEGER,
	snSwPortInLinePowerClass
	    INTEGER,
	snSwPortInLinePowerPriority
	    INTEGER,
	snSwPortInfoMirrorMode
	    INTEGER,
	snSwPortStatsInJumboFrames
	    Counter64,
	snSwPortStatsOutJumboFrames
	    Counter64,
	snSwPortInLinePowerConsumed
	    INTEGER,
	snSwPortInLinePowerPDType
	    DisplayString
	}

snSwPortInfoPortNum OBJECT-TYPE
	SYNTAX  INTEGER
	ACCESS  read-only
	STATUS  deprecated
	DESCRIPTION
		"The port index.
		 The bit 0 to bit 7: port number. 
		 The bit 8 to bit 11: slot number (slot for chassis only)."
	::= { snSwPortInfoEntry 1 }


snSwPortInfoMonitorMode OBJECT-TYPE
	SYNTAX  INTEGER {
		disabled(0),
		input(1),
		output(2),
		both(3)
		}
	ACCESS  read-write
	STATUS  deprecated
	DESCRIPTION
		"DEPRECATED by snSwPortInfoMirrorMode and
		snPortMonitorTable."
	::= { snSwPortInfoEntry 2 }


snSwPortInfoTagMode OBJECT-TYPE
	SYNTAX  INTEGER {
		tagged(1),      
		untagged(2),    
		auto(3),
		disabled(4)
		}
	ACCESS  read-write
	STATUS  deprecated
	DESCRIPTION
		"For tagged port, we could have multiple VLANs 
		 per port. For untagged port or auto port, there 
		 is only one VLAN ID per port."  
	::= { snSwPortInfoEntry 3 }


snSwPortInfoChnMode OBJECT-TYPE
	SYNTAX  INTEGER {
        none(0),
		halfDuplex(1),  
		fullDuplex(2)   
		}
	ACCESS  read-write
	STATUS  deprecated
	DESCRIPTION
		"The port can be configured to operate in either
		half or full duplex mode. The values are:
			halfDuplex(1)...half duplex mode
			fullDuplex(2)...full duplex mode
		The read-back channel status from hardware are:
            none(0).........link down or port disabled.
			halfDuplex(1)...half duplex mode
			fullDuplex(2)...full duplex mode
		
		The port media type (expansion or regular)
		and port link type (trunk or feeder) determine
		value of this object.
		The port can not set to half duplex mode
		if the port connect mode is m200e(4).
		However, the value of this parameter may be
		automatically set whenever the expansion port
		is connected (e.g. cascade connecting device)."
	::= { snSwPortInfoEntry 4 }


snSwPortInfoSpeed OBJECT-TYPE
	SYNTAX  INTEGER {
        none(0),
	    sAutoSense(1),
		s10M(2),
		s100M(3),
		s1G(4),
		s1GM(5),
		s155M(6),
		s10G(7)
		}
	ACCESS  read-write
	STATUS  deprecated
	DESCRIPTION     
		"The speed configuration for a port. The values are:
          none(0)..........link down or no traffic.
		  sAutoSense(1)....Auto-sensing 10 or 100Mbits.
		  s10M(2)..........10Mbits per second.
		  s100M(3).........100Mbits per second.
		  s1G(4)...........1Gbits per second.
		  s1GM(5)..........1Gbits per second master.
		  s155M(6).........155Mbits per second (ATM) (for expansion board only).
		  s10G(7)..........10Gbits per second.

         The read-back hardware status are the following:
          none(0)..........link down or no traffic.
		  s10M(2)..........10Mbits per second.
		  s100M(3).........100Mbits per second.
		  s1G(4)...........1Gbits per second.
		  s1GM(5)..........1Gbits per second master.
		  s155M(6).........155Mbits per second (ATM) (for expansion board only).
		  s10G(7)..........10Gbits per second.

		The port media type (expansion or regular)
		and port link type (trunk or feeder) determine
		whether this object can be written and the valid
		values.
		It is not allowed to change speed for trunks ports.
		For expansion ports, all of the above speed 
		can be set.
		However, the value of this parameter may be
		automatically set whenever the expansion port
		is connected (e.g. cascade connecting device)."
	::= { snSwPortInfoEntry 5 }



snSwPortInfoMediaType OBJECT-TYPE
	SYNTAX  INTEGER {
	        other(1),
		m100BaseTX(2),
		m100BaseFX(3),
		m1000BaseFX(4),
		mT3(5),
		m155ATM(6),
		m1000BaseTX(7),
		m622ATM(8),
		m155POS(9),
		m622POS(10),
		m2488POS(11),
		m10000BaseFX(12)
		}
	ACCESS  read-only
	STATUS  deprecated
	DESCRIPTION 
		"The media type for the port. The
		values are:
		  other(1).........other or unknown media.
		  m100BaseTX(2)....100Mbits per second copper.
		  m100BaseFX(3)....100Mbits per second fiber.
		  m1000BaseFX(4)...1Gbits per second fiber.
		  mT3(5)...........45Mbits per second (T3).
		  m155ATM(6).......155Mbits per second (ATM).
		  m1000BaseTX(7)...1Gbits per second copper.
		  m622ATM(8).......622Mbits per second (ATM).
		  m155POS(9).......155Mbits per second (POS).
		  m622POS(10)......622Mbits per second (POS).
		  m2488POS(11).....2488Mbits per second (POS).
		  m10000BaseFX(12).10Gbits per second fiber."
	::= { snSwPortInfoEntry 6 }



snSwPortInfoConnectorType OBJECT-TYPE
	SYNTAX  INTEGER {
		other(1),
		copper(2),
		fiber(3)
		}
	ACCESS  read-only
	STATUS  deprecated
	DESCRIPTION 
		"The type of connector that the port offers.
		 The values are:
		  other(1)...........other or unknown connector
		  copper(2)..........Copper connector
		  fiber(3)...........Fiber connector
		 This describes the physical connector type"
	::= { snSwPortInfoEntry 7 }


snSwPortInfoAdminStatus OBJECT-TYPE
    SYNTAX  INTEGER {
		up(1),       -- ready to pass packets
		down(2),
		testing(3)   -- in some test mode
		}
    ACCESS  read-write
    STATUS  deprecated
    DESCRIPTION
		"The desired state of all ports.  The
	 	testing(3) state indicates that no operational
	 	packets can be passed. 
	 	(same as ifAdminStatus in MIB-II)"
    ::= { snSwPortInfoEntry 8 }


snSwPortInfoLinkStatus OBJECT-TYPE
    SYNTAX  INTEGER {
    	up(1),       -- ready to pass packets
    	down(2),
    	testing(3)   -- in some test mode
        }
    ACCESS  read-only
    STATUS  deprecated
    DESCRIPTION
        "The current operational state of the interface.
         The testing(3) state indicates that no operational
         packets can be passed. 
         (same as ifOperStatus in MIB-II)"
    ::= { snSwPortInfoEntry 9 }


snSwPortInfoPortQos OBJECT-TYPE
	SYNTAX  INTEGER {
		level0(0),
		level1(1),
		level2(2),
		level3(3),
		level4(4),
		level5(5),
		level6(6),
		level7(7)
		}
	ACCESS  read-write
	STATUS  deprecated
	DESCRIPTION
		"The Stand alone stackable switch Port Qos Priority values are:
		 low(0)   -- low prority
		 high(1) -- high prority.
		 The BigIron Port Qos Priority values are:
		level0(0), level1(1), level2(2), level3(3),
		level4(4), level5(5), level6(6), level7(7) "
	::= { snSwPortInfoEntry 10 }


snSwPortInfoPhysAddress OBJECT-TYPE
	SYNTAX  PhysAddress
	ACCESS  read-only
	STATUS  deprecated
	DESCRIPTION
		"The port physical address. The physical address 
		represents the switch port."
	::= { snSwPortInfoEntry 11 }



snSwPortStatsInFrames OBJECT-TYPE
    SYNTAX  Counter
    ACCESS  read-only
    STATUS  deprecated
    DESCRIPTION
    	"The total number of packets received on the interface."
    ::= { snSwPortInfoEntry 12 }


snSwPortStatsOutFrames OBJECT-TYPE
    SYNTAX  Counter
    ACCESS  read-only
    STATUS  deprecated
    DESCRIPTION
    	"The total number of packets transmitted out of the interface."
    ::= { snSwPortInfoEntry 13 }


snSwPortStatsAlignErrors   OBJECT-TYPE
     SYNTAX     Counter
     ACCESS     read-only
     STATUS     deprecated
     DESCRIPTION
	 	"dot3StatsAlignmentErrors : A count of frames 
	  	received on a particular interface that are 
	  	not an integral number of octets in length 
	  	and do not pass the FCS check.

	  	The count represented by an instance of this
	  	object is incremented when the alignmentError
	  	status is returned by the MAC service to the
	  	LLC (or other MAC user). Received frames for
	  	which multiple error conditions obtain are,
	  	according to the conventions of IEEE 802.3
	  	Layer Management, counted exclusively according
	  	to the error status presented to the LLC."
    ::= { snSwPortInfoEntry 14 }

snSwPortStatsFCSErrors   OBJECT-TYPE
     SYNTAX      Counter
     ACCESS      read-only
     STATUS      deprecated
     DESCRIPTION
	 	"dot3StatsFCSErrors : A count of frames received 
	  	on a particular interface that are an integral 
	  	number of octets in length but do not pass the 
	  	FCS check.

	  	The count represented by an instance of this
	  	object is incremented when the frameCheckError
	  	status is returned by the MAC service to the
	  	LLC (or other MAC user). Received frames for
	  	which multiple error conditions obtain are,
	  	according to the conventions of IEEE 802.3
	  	Layer Management, counted exclusively according
	  	to the error status presented to the LLC."
    ::= { snSwPortInfoEntry 15 }


snSwPortStatsMultiColliFrames   OBJECT-TYPE
     SYNTAX      Counter
     ACCESS      read-only
     STATUS      deprecated
     DESCRIPTION
	 	"dot3StatsMultipleCollisionFrames : 
	  	A count of successfully transmitted frames on
	  	a particular interface for which transmission
	  	is inhibited by more than one collision.

	  	A frame that is counted by an instance of this
	  	object is also counted by the corresponding
	  	instance of either the ifOutUcastPkts,
	  	ifOutMulticastPkts, or ifOutBroadcastPkts,
	  	and is not counted by the corresponding
	  	instance of the dot3StatsSingleCollisionFrames
	  	object."
    ::= { snSwPortInfoEntry 16 }


snSwPortStatsFrameTooLongs   OBJECT-TYPE
     SYNTAX    Counter
     ACCESS    read-only
     STATUS    deprecated
     DESCRIPTION
	 	"dot3StatsFrameTooLongs : A count of frames 
	  	received on a particular interface that 
	  	exceed the maximum permitted frame size.

	  	The count represented by an instance of this
	  	object is incremented when the frameTooLong
	  	status is returned by the MAC service to the
	  	LLC (or other MAC user). Received frames for
	  	which multiple error conditions obtain are,
	  	according to the conventions of IEEE 802.3
	  	Layer Management, counted exclusively according
	  	to the error status presented to the LLC."
    ::= { snSwPortInfoEntry 17 }


snSwPortStatsTxColliFrames   OBJECT-TYPE
     SYNTAX      Counter
     ACCESS      read-only
     STATUS      deprecated
     DESCRIPTION
	 	"A count of successfully transmitted frames on
	  	a particular interface for which transmission
	  	is inhibited by more than one collision.

	  	A frame that is counted by a combination of
		both dot3StatsSingleCollisionFrames and
		dot3StatsMultipleCollisionFrames objects."
    ::= { snSwPortInfoEntry 18 }

snSwPortStatsRxColliFrames   OBJECT-TYPE
     SYNTAX      Counter
     ACCESS      read-only
     STATUS      deprecated
     DESCRIPTION
	 	"A count of successfully received frames on
	  	a particular interface for which transmission
	  	is inhibited by more than one collision.  This
	  	object is not specified in dot3 but it has the
	  	same functionarity as snSwPortStatsTxColliFrames."
    ::= { snSwPortInfoEntry 19 }

snSwPortStatsFrameTooShorts   OBJECT-TYPE
     SYNTAX    Counter
     ACCESS    read-only
     STATUS    deprecated
     DESCRIPTION
	 	" A count of frames received on a particular 
	 	interface that below the minimum permitted 
	 	frame size."
    ::= { snSwPortInfoEntry 20 }

snSwPortLockAddressCount OBJECT-TYPE
     SYNTAX  INTEGER (0..2048)
     ACCESS  read-write
     STATUS  deprecated
     DESCRIPTION
	 	"The number of source MAC addresses are allowed
	 	for a port. Writing 0 to this object will allow
	 	any number of addresses."
    DEFVAL { 8 }
    ::= { snSwPortInfoEntry 21 }

snSwPortStpPortEnable OBJECT-TYPE
     SYNTAX  INTEGER {
               disabled(0),
               enabled(1)
             }
     ACCESS  read-write
     STATUS  deprecated
     DESCRIPTION
        "The enabled/disabled status of the port."
     REFERENCE
     	"IEEE 802.1D-1990: Section 4.5.5.2, dot1dStpPortEnable"
     ::= { snSwPortInfoEntry 22 }

snSwPortDhcpGateListId OBJECT-TYPE
	SYNTAX  INTEGER (0..32)
	ACCESS  read-write
	STATUS  deprecated
	DESCRIPTION
		"The ID for a DHCP gateway list entry relative 
		 to this switch port. 0 = unset or no assigned ID"
	::= { snSwPortInfoEntry 23 }

snSwPortName OBJECT-TYPE
	SYNTAX	DisplayString (SIZE(0..255))
	ACCESS	read-write
	STATUS	deprecated
	DESCRIPTION
		"Port Name string."
	::= { snSwPortInfoEntry 24 }

snSwPortStatsInBcastFrames OBJECT-TYPE
    SYNTAX  Counter
    ACCESS  read-only
    STATUS  deprecated
    DESCRIPTION
    	"The total number of broadcast packets received on the interface."
    ::= { snSwPortInfoEntry 25 }


snSwPortStatsOutBcastFrames OBJECT-TYPE
    SYNTAX  Counter
    ACCESS  read-only
    STATUS  deprecated
    DESCRIPTION
    	"The total number of broadcast packets transmitted out of the interface."
    ::= { snSwPortInfoEntry 26 }

snSwPortStatsInMcastFrames OBJECT-TYPE
    SYNTAX  Counter
    ACCESS  read-only
    STATUS  deprecated
    DESCRIPTION
    	"The total number of multicast packets received on the interface."
    ::= { snSwPortInfoEntry 27 }


snSwPortStatsOutMcastFrames OBJECT-TYPE
    SYNTAX  Counter
    ACCESS  read-only
    STATUS  deprecated
    DESCRIPTION
    	"The total number of multicast packets transmitted out of the interface."
    ::= { snSwPortInfoEntry 28 }


snSwPortStatsInDiscard OBJECT-TYPE
    SYNTAX  Counter
    ACCESS  read-only
    STATUS  deprecated
    DESCRIPTION
        "The number of inbound packets which were chosen
         to be discarded even though no errors had been
         detected to prevent their being deliverable to a
         higher-layer protocol.  One possible reason for
         discarding such a packet could be to free up
         buffer space."
    ::= { snSwPortInfoEntry 29 }


snSwPortStatsOutDiscard OBJECT-TYPE
    SYNTAX  Counter
    ACCESS  read-only
    STATUS  deprecated
    DESCRIPTION
        "The number of outbound packets which were chosen
         to be discarded even though no errors had been
         detected to prevent their being transmitted.  One
         possible reason for discarding such a packet could
         be to free up buffer space."
    ::= { snSwPortInfoEntry 30 }

snSwPortStatsMacStations OBJECT-TYPE
    SYNTAX  INTEGER
    ACCESS  read-only
    STATUS  deprecated
    DESCRIPTION
    	"The total number of MAC Stations connected to the interface."
    ::= { snSwPortInfoEntry 31 }


snSwPortCacheGroupId OBJECT-TYPE
    SYNTAX  INTEGER
    ACCESS  read-write
    STATUS  deprecated
    DESCRIPTION
    	"Cache Group ID for the interface."
    ::= { snSwPortInfoEntry 32 }

snSwPortTransGroupId OBJECT-TYPE
    SYNTAX  INTEGER
    ACCESS  read-write
    STATUS  deprecated
    DESCRIPTION
    	"Transparent Group ID for the interface."
    ::= { snSwPortInfoEntry 33 }

snSwPortInfoAutoNegotiate OBJECT-TYPE
	SYNTAX  INTEGER {
		disabled(0),
		enabled(1),
		negFullAuto(2),
		global(3),
		other(4)
		}
	ACCESS  read-write
	STATUS  deprecated
	DESCRIPTION
		"This feature only applies to Gigabit Ethernet ports. If set to
		disable(0), port will be put to non-negotiation mode. If set to
		enable(1), port will start auto-negotiation indefinitely until
		succeed. If set to negFullAuto(2), the port will start with auto-
		negotiation, if the negotiation failed, then it will automatically
		switch to non-negotiation mode. Stackable products (except TurboIron
		8) Gigabit Ethernet ports do not support negFullAuto(2). If set
		to global(3), port negotiation mode follows the value of
		snSwGlobalAutoNegotiate. Non-Gigabit Ethernet port returns
		the value other(4)."
    DEFVAL { global }
	::= { snSwPortInfoEntry 34 }


snSwPortInfoFlowControl OBJECT-TYPE
	SYNTAX  INTEGER {
		disabled(0),
		enabled(1)
		}
	ACCESS  read-write
	STATUS  deprecated
	DESCRIPTION
		"Enable/Disbale port flow control."
    DEFVAL { enabled }
	::= { snSwPortInfoEntry 35 }

snSwPortInfoGigType OBJECT-TYPE
	SYNTAX  INTEGER {
		m1000BaseSX(0),
		m1000BaseLX(1),
		m1000BaseLH(2),
		m1000BaseLHA(3),
		m1000BaseLHB(4),
		m1000BaseTX(5),
		m10000BaseSR(6),
		m10000BaseLR(7),
		m10000BaseER(8),
		sfpCWDM1470nm80Km(9),
		sfpCWDM1490nm80Km(10),
		sfpCWDM1510nm80Km(11),
		sfpCWDM1530nm80Km(12),
		sfpCWDM1550nm80Km(13),
		sfpCWDM1570nm80Km(14),
		sfpCWDM1590nm80Km(15),
		sfpCWDM1610nm80Km(16),
		sfpCWDM1470nm100Km(17),
		sfpCWDM1490nm100Km(18),
		sfpCWDM1510nm100Km(19),
		sfpCWDM1530nm100Km(20),
		sfpCWDM1550nm100Km(21),
		sfpCWDM1570nm100Km(22),
		sfpCWDM1590nm100Km(23),
		sfpCWDM1610nm100Km(24),
		m1000BaseLHX(25),
		notApplicable(255)
		}
	ACCESS  read-only
	STATUS  deprecated
	DESCRIPTION 
		"The media type for the port. The
		values are:
		  m1000BaseSX(0)....1Gbits per second fiber, with a short wavelength transceiver.
		  m1000BaseLX(1)....1Gbits per second fiber, with a long wavelength transceiver (3km).
		  m1000BaseLH(2)....1Gbits per second fiber, with a special wavelength transceiver (50km).
		  m1000BaseLHA(3)....1Gbits per second fiber, with a special wavelength transceiver (70km).
		  m1000BaseLHB(4)....1Gbits per second fiber, with a special wavelength transceiver (150km).
		  m1000BaseTX(5)....1Gbits per second copper (100meter).
		  m10000BaseSR(6)....10Gbits per second fiber, with a short range wavelength transceiver (100m).
		  m10000BaseLR(7)....10Gbits per second fiber, with a long range wavelength transceiver (10km).
		  m10000BaseER(8)....10Gbits per second fiber, with a extended range wavelength transceiver (40km).
		  sfpCWDM1470nm80Km(9)....1Gbits per second CWDM fiber, with a wavelength 1470nm, reach 80 kms.
		  sfpCWDM1490nm80Km(10)....1Gbits per second CWDM fiber, with a wavelength 1490nm, reach 80 kms.
		  sfpCWDM1510nm80Km(11)....1Gbits per second CWDM fiber, with a wavelength 1510nm, reach 80 kms.
		  sfpCWDM1530nm80Km(12)....1Gbits per second CWDM fiber, with a wavelength 1530nm, reach 80 kms.
		  sfpCWDM1550nm80Km(13)....1Gbits per second CWDM fiber, with a wavelength 1550nm, reach 80 kms.
		  sfpCWDM1570nm80Km(14)....1Gbits per second CWDM fiber, with a wavelength 1570nm, reach 80 kms.
		  sfpCWDM1590nm80Km(15)....1Gbits per second CWDM fiber, with a wavelength 1590nm, reach 80 kms.
		  sfpCWDM1610nm80Km(16)....1Gbits per second CWDM fiber, with a wavelength 1610nm, reach 80 kms.
		  sfpCWDM1470nm100Km(17)....1Gbits per second CWDM fiber, with a wavelength 1470nm, reach 100 kms.
		  sfpCWDM1490nm100Km(18)....1Gbits per second CWDM fiber, with a wavelength 1490nm, reach 100 kms.
		  sfpCWDM1510nm100Km(19)....1Gbits per second CWDM fiber, with a wavelength 1510nm, reach 100 kms.
		  sfpCWDM1530nm100Km(20)....1Gbits per second CWDM fiber, with a wavelength 1530nm, reach 100 kms.
		  sfpCWDM1550nm100Km(21)....1Gbits per second CWDM fiber, with a wavelength 1550nm, reach 100 kms.
		  sfpCWDM1570nm100Km(22)....1Gbits per second CWDM fiber, with a wavelength 1570nm, reach 100 kms.
		  sfpCWDM1590nm100Km(23)....1Gbits per second CWDM fiber, with a wavelength 1590nm, reach 100 kms.
		  sfpCWDM1610nm100Km(24)....1Gbits per second CWDM fiber, with a wavelength 1610nm, reach 100 kms.
		  m1000BaseLHX(25)...1Gbits per second fiber, with a special wavelength transceiver (150km).
		  notApplicable(255)....a non-gigabit port."
	::= { snSwPortInfoEntry 36 }


snSwPortStatsLinkChange OBJECT-TYPE
    SYNTAX  Counter
    ACCESS  read-only
    STATUS  deprecated
    DESCRIPTION
    	"The total number of link state change of the interface."
    ::= { snSwPortInfoEntry 37 }


snSwPortIfIndex OBJECT-TYPE
    SYNTAX  INTEGER
    ACCESS  read-only
    STATUS  deprecated
    DESCRIPTION
    	"In order to identify a particular interface, this
		object shall identify the instance of the ifIndex
		object, defined in RFC 1213 and RFC 1573."
    ::= { snSwPortInfoEntry 38 }


snSwPortDescr OBJECT-TYPE
    SYNTAX  DisplayString
    ACCESS  read-only
    STATUS  deprecated
    DESCRIPTION
    	"A textual string containing the slot/port information
    	about the interface."
    ::= { snSwPortInfoEntry 39 }


snSwPortInOctets OBJECT-TYPE
    SYNTAX  OCTET STRING (SIZE(8))
    ACCESS  read-only
    STATUS  deprecated
    DESCRIPTION
    	"The total number of octets received on the interface,
    	including framing characters. This object is a 64-bit
		counter of the ifInOctets object, defined in RFC 1213.
		The octet string is in big-endian byte order."
    ::= { snSwPortInfoEntry 40 }


snSwPortOutOctets OBJECT-TYPE
    SYNTAX  OCTET STRING (SIZE(8))
    ACCESS  read-only
    STATUS  deprecated
    DESCRIPTION
    	"The total number of octets transmitted out of the interface,
    	including framing characters. This object is a 64-bit
		counter of the ifOutOctets object, defined in RFC 1213.
		The octet string is in big-endian byte order."
    ::= { snSwPortInfoEntry 41 }


snSwPortStatsInBitsPerSec OBJECT-TYPE
    SYNTAX  Gauge
    ACCESS  read-only
    STATUS  deprecated
    DESCRIPTION
    	"The number of bits per second received on the interface
    	over a 5 minutes interval."
    ::= { snSwPortInfoEntry 42 }


snSwPortStatsOutBitsPerSec OBJECT-TYPE
    SYNTAX  Gauge
    ACCESS  read-only
    STATUS  deprecated
    DESCRIPTION
    	"The number of bits per second transmitted out of the interface
    	over a 5 minutes interval."
    ::= { snSwPortInfoEntry 43 }


snSwPortStatsInPktsPerSec OBJECT-TYPE
    SYNTAX  Gauge
    ACCESS  read-only
    STATUS  deprecated
    DESCRIPTION
    	"The number of packets per second received on the interface
    	over a 5 minutes interval."
    ::= { snSwPortInfoEntry 44 }


snSwPortStatsOutPktsPerSec OBJECT-TYPE
    SYNTAX  Gauge
    ACCESS  read-only
    STATUS  deprecated
    DESCRIPTION
    	"The number of packets per second transmitted out of the interface
    	over a 5 minutes interval."
    ::= { snSwPortInfoEntry 45 }


snSwPortStatsInUtilization OBJECT-TYPE
    SYNTAX  INTEGER (0..10000)
    ACCESS  read-only
    STATUS  deprecated
    DESCRIPTION
    	"The input network utilization in hundredths of a percent
    	over a 5 minutes interval."
    ::= { snSwPortInfoEntry 46 }


snSwPortStatsOutUtilization OBJECT-TYPE
    SYNTAX  INTEGER (0..10000)
    ACCESS  read-only
    STATUS  deprecated
    DESCRIPTION
    	"The output network utilization in hundredths of a percent
    	over a 5 minutes interval."
    ::= { snSwPortInfoEntry 47 }

snSwPortFastSpanPortEnable OBJECT-TYPE
     SYNTAX  INTEGER {
               disabled(0),
               enabled(1)
             }
     ACCESS  read-write
     STATUS  deprecated
     DESCRIPTION
        "The enabled/disabled fast span port status of the port."
     ::= { snSwPortInfoEntry 48 }

snSwPortFastSpanUplinkEnable OBJECT-TYPE
     SYNTAX  INTEGER {
               disabled(0),
               enabled(1)
             }
     ACCESS  read-write
     STATUS  deprecated
     DESCRIPTION
        "The enabled/disabled fast span uplink status of the port."
     ::= { snSwPortInfoEntry 49 }

snSwPortVlanId OBJECT-TYPE
     SYNTAX  INTEGER (0..4095)
     ACCESS  read-write
     STATUS  deprecated
     DESCRIPTION
        "The ID of a VLAN of which this port is a member. Port must
        be untagged. For tagged port which belongs to multiple
        VLANs, this object return 0 which is an invalid VLAN ID
        value."
     ::= { snSwPortInfoEntry 50 }

snSwPortRouteOnly OBJECT-TYPE
     SYNTAX  INTEGER { disabled(0), enabled(1) }
     ACCESS  read-write
     STATUS  deprecated
     DESCRIPTION
        "Enable/Disable L2 switching of a routing switch port.
		By default, the routing switch performs routing first.
		If routing failed, it performs switching. Enable route
		only instrcuts the routing switch to perform routing
		only. For a L2 switching only product, reading this
		object always return 'disabled', writing 'enabled' to
		this object takes no effect."
     DEFVAL { disabled }
     ::= { snSwPortInfoEntry 51 }

snSwPortPresent OBJECT-TYPE
     SYNTAX  INTEGER {
               false(0),
               true(1)
             }
     ACCESS  read-only
     STATUS  deprecated
     DESCRIPTION
        "Indicate if the port is absent or present.
		 This object only valid for M4 module
		 "
     ::= { snSwPortInfoEntry 52 }

snSwPortGBICStatus OBJECT-TYPE
     SYNTAX  INTEGER {
               gbic(1),
               miniGBIC(2),
               empty(3),
               other(4)
             }
     ACCESS  read-only
     STATUS  deprecated
     DESCRIPTION
        "Indicate if the gig port has GBICs on them.
		 If set to  GBIC(1), it means that the port is GBIC.
		 If set to  miniGBIC(2), it means that the port miniGBIC.
		 If set to empty(3), it means that the GBIC is missing.
		 Value other(4) means that the port not a removable gig port.
		 "
     ::= { snSwPortInfoEntry 53 }

snSwPortStatsInKiloBitsPerSec OBJECT-TYPE
    SYNTAX  Unsigned32
    ACCESS  read-only
    STATUS  deprecated
    DESCRIPTION
    	"Bit rate in kilobits per second received on the 10G and faster interface
    	over a 5 minutes interval."
    ::= { snSwPortInfoEntry 54 }


snSwPortStatsOutKiloBitsPerSec OBJECT-TYPE
    SYNTAX  Unsigned32
    ACCESS  read-only
    STATUS  deprecated
    DESCRIPTION
    	"Bit rate in kilobits per second transmitted out of the 10G and faster interface
    	over a 5 minutes interval."
    ::= { snSwPortInfoEntry 55 }

snSwPortLoadInterval OBJECT-TYPE
     SYNTAX  INTEGER (30..300)
     ACCESS  read-write
     STATUS  deprecated
     DESCRIPTION
        "The time in seconds for which average port utilization should be carried out.
        The value should be incremental of 30 seconds, between the ranges specified."
     DEFVAL { 300 }
     ::= { snSwPortInfoEntry 56 }

snSwPortTagType OBJECT-TYPE
     SYNTAX  INTEGER
     ACCESS  read-write
     STATUS  deprecated
     DESCRIPTION
		"The IEEE802.1q tag type embedded in the length/type field of
		an Ethernet packet. It specifies that the 2 octets after the
		length/type field in an Ethernet packet is the tag value."
     DEFVAL { 33024 }
     ::= { snSwPortInfoEntry 57 }

snSwPortInLinePowerControl OBJECT-TYPE
     SYNTAX  INTEGER {
               other(1),
               disable(2),
               enable(3),
               enableLegacyDevice(4)
             }
     ACCESS  read-write
     STATUS  deprecated
     DESCRIPTION
		"Control inline power on/off to a port. If a port does not
		have inline power capability, reading this object returns
		'other(1)'."
     ::= { snSwPortInfoEntry 58 }

snSwPortInLinePowerWattage OBJECT-TYPE
     SYNTAX  INTEGER
     ACCESS  read-write
     STATUS  deprecated
     DESCRIPTION
		"Adjust the inline power wattage. Valid value between 
		1000 and 15400. Each unit is milliwatts.
		This object can only be set after snSwPortInLinePowerControl
		has been set to 'enable(3)' or 'enableLegacyDevice(4)'. If
		a port does not have inline power capability, reading this
		object returns undefined value."
     ::= { snSwPortInfoEntry 59 }

snSwPortInLinePowerClass OBJECT-TYPE
     SYNTAX  INTEGER (0..3)
     ACCESS  read-write
     STATUS  deprecated
     DESCRIPTION
		"Adjust the inline power class. This object can only be set
		after snSwPortInLinePowerControl has been set to 'enable(3)'
		or 'enableLegacyDevice(4)'. If a port does not have inline
		power capability, reading this object returns undefined value."
     ::= { snSwPortInfoEntry 60 }

snSwPortInLinePowerPriority OBJECT-TYPE
     SYNTAX  INTEGER {
               invalid(0),
               critical(1),
               high(2),
               low(3),
               medium(4),
               other(5)
             }
     ACCESS  read-write
     STATUS  deprecated
     DESCRIPTION
		"Inline power allocation priority for the power device
		 0- Not a POE port, 1- Critical, 2- High, 3- Low,
		 4- Medium, 5- other."
     ::= { snSwPortInfoEntry 61 }

snSwPortInfoMirrorMode OBJECT-TYPE
     SYNTAX  INTEGER {
               disable(0),
               enable(1)
             }
     ACCESS  read-write
     STATUS  deprecated
     DESCRIPTION
             "Enable/disable mirror on this port."
     ::= { snSwPortInfoEntry 62 }

snSwPortStatsInJumboFrames OBJECT-TYPE
    SYNTAX  Counter64
    ACCESS  read-only
    STATUS  deprecated
    DESCRIPTION
    	"The total number of jumbo packets received on the interface."
    ::= { snSwPortInfoEntry 63 }

snSwPortStatsOutJumboFrames OBJECT-TYPE
    SYNTAX  Counter64
    ACCESS  read-only
    STATUS  deprecated
    DESCRIPTION
    	"The total number of jumbo packets transmitted out of the interface."
    ::= { snSwPortInfoEntry 64 }

snSwPortInLinePowerConsumed OBJECT-TYPE
     SYNTAX  INTEGER
     ACCESS  read-only
     STATUS  deprecated
     DESCRIPTION
		"Inline power consumed by the port. Each unit is milliwatts."
     ::= { snSwPortInfoEntry 66 }

snSwPortInLinePowerPDType OBJECT-TYPE
	 SYNTAX	DisplayString
     ACCESS  read-only
     STATUS  deprecated
     DESCRIPTION
		"Inline Power device type	802.3af or Legacy device."
     ::= { snSwPortInfoEntry 67 }
-- end of deprecated snSwPortInfoTable


-- Switch Port Information Group
-- snSwIfInfoTable which is indexed by ifIndex port format is replacing the
-- snSwPortInfoTable which is indexed by a proprietary port format.

snSwIfInfoTable OBJECT-TYPE
	SYNTAX  SEQUENCE OF SnSwIfInfoEntry
	ACCESS  not-accessible
	STATUS  mandatory
	DESCRIPTION
		"A specific snSwIfInfo group consists of a number of 
		 switch ports.  "
	::= { snSwPortInfo 5 }

snSwIfInfoEntry OBJECT-TYPE
	SYNTAX  SnSwIfInfoEntry
	ACCESS  not-accessible
	STATUS  mandatory
	DESCRIPTION
		"An entry in the snSwIfInfo table indicates the 
		 configuration on a specified port. A SNMP SET PDU 
		 for a row of the snSwIfInfoTable requires the entire 
		 sequence of the MIB Objects in each 
		 snSwIfInfoEntry stored in one PDU.  Otherwise, 
	 	 GENERR return-value will be returned."
	INDEX   { snSwIfInfoPortNum }
	::= { snSwIfInfoTable 1 }

SnSwIfInfoEntry ::= SEQUENCE {
	snSwIfInfoPortNum
		InterfaceIndex,
	snSwIfInfoMonitorMode
	    INTEGER,
	snSwIfInfoMirrorPorts
	    OCTET STRING,
	snSwIfInfoTagMode
		INTEGER,
	snSwIfInfoTagType
	    INTEGER,
	snSwIfInfoChnMode
	    INTEGER,
	snSwIfInfoSpeed
	    INTEGER,
    snSwIfInfoMediaType
	    INTEGER,
	snSwIfInfoConnectorType
	    INTEGER,
	snSwIfInfoAdminStatus
		INTEGER,
	snSwIfInfoLinkStatus
		INTEGER,
	snSwIfInfoPortQos
	    INTEGER,
	snSwIfInfoPhysAddress
	    PhysAddress,
	snSwIfLockAddressCount
	    INTEGER,
	snSwIfStpPortEnable
	    INTEGER,
    snSwIfDhcpGateListId
	    INTEGER,
	snSwIfName
		DisplayString,
	snSwIfDescr
	    DisplayString,
	snSwIfInfoAutoNegotiate
	    INTEGER,
	snSwIfInfoFlowControl
	    INTEGER,
	snSwIfInfoGigType
	    INTEGER,
	snSwIfFastSpanPortEnable
	    INTEGER,
	snSwIfFastSpanUplinkEnable
	    INTEGER,
	snSwIfVlanId
	    INTEGER,
	snSwIfRouteOnly
	    INTEGER,
	snSwIfPresent
	    INTEGER,
	snSwIfGBICStatus
	    INTEGER,
	snSwIfLoadInterval
	    INTEGER (30..300),
    snSwIfStatsInFrames 
    	Counter32,
	snSwIfStatsOutFrames 
    	Counter32,
	snSwIfStatsAlignErrors            
		Counter32,
    snSwIfStatsFCSErrors                  
		Counter32,
    snSwIfStatsMultiColliFrames    
		Counter32,
	snSwIfStatsTxColliFrames
	    Counter32,
	snSwIfStatsRxColliFrames
	    Counter32,
    snSwIfStatsFrameTooLongs              
		Counter32,
	snSwIfStatsFrameTooShorts
	    Counter32,
	snSwIfStatsInBcastFrames
	    Counter32,
	snSwIfStatsOutBcastFrames
	    Counter32,
	snSwIfStatsInMcastFrames
	    Counter32,
	snSwIfStatsOutMcastFrames
	    Counter32,
	snSwIfStatsInDiscard
	    Counter32,
	snSwIfStatsOutDiscard
	    Counter32,
	snSwIfStatsMacStations
	    INTEGER,
	snSwIfStatsLinkChange
	    Counter32,
	snSwIfInOctets
	    Counter64,
	snSwIfOutOctets
	    Counter64,
	snSwIfStatsInBitsPerSec
	    Gauge32,
	snSwIfStatsOutBitsPerSec
	    Gauge32,
	snSwIfStatsInPktsPerSec
	    Gauge32,
	snSwIfStatsOutPktsPerSec
	    Gauge32,
	snSwIfStatsInUtilization
	    INTEGER (0..10000),
	snSwIfStatsOutUtilization
	    INTEGER (0..10000),
	snSwIfStatsInKiloBitsPerSec
		Unsigned32,
	snSwIfStatsOutKiloBitsPerSec    
		Unsigned32,
	snSwIfStatsInJumboFrames
	    Counter64,
	snSwIfStatsOutJumboFrames
	    Counter64,
	snSwIfInfoMirrorMode
	    INTEGER
	}

snSwIfInfoPortNum OBJECT-TYPE
	SYNTAX	InterfaceIndex
	ACCESS  read-only
	STATUS	mandatory
	DESCRIPTION
		"The port/interface index (ifindex)."
	::= { snSwIfInfoEntry 1 }

snSwIfInfoMonitorMode OBJECT-TYPE
	SYNTAX  INTEGER {
				disabled(0),
				input(1),
				output(2),
				both(3)
			}
	ACCESS  read-write
	STATUS  deprecated
	DESCRIPTION
		"DEPRECATED by snSwIf2MirrorMode and
		snPortMonitorTable."
	::= { snSwIfInfoEntry 2 }

snSwIfInfoMirrorPorts OBJECT-TYPE
	SYNTAX		OCTET STRING
	ACCESS  read-write
	STATUS		mandatory
	DESCRIPTION
		"The list of port/interface index (ifindex), which mirror this interface,
		 when monitoring is enabled."
	::= { snSwIfInfoEntry 3 }

snSwIfInfoTagMode OBJECT-TYPE
	SYNTAX  INTEGER {
				tagged(1),      
				untagged(2)
			}
	ACCESS  read-write
	STATUS  mandatory
	DESCRIPTION
		"For tagged port, we could have multiple VLANs 
		 per port. For untagged port, there 
		 is only one VLAN ID per port."  
	::= { snSwIfInfoEntry 4 }

snSwIfInfoTagType OBJECT-TYPE
     SYNTAX  INTEGER
     ACCESS  read-write
     STATUS  mandatory
     DESCRIPTION
		"The IEEE802.1q tag type embedded in the length/type field of
		an Ethernet packet. It specifies that the 2 octets after the
		length/type field in an Ethernet packet is the tag value."
     DEFVAL { 33024 }
     ::= { snSwIfInfoEntry 5 }

snSwIfInfoChnMode OBJECT-TYPE
	SYNTAX  INTEGER {
				none(0),
				halfDuplex(1),  
				fullDuplex(2)   
			}
	ACCESS  read-write
	STATUS  mandatory
	DESCRIPTION
		"The port can be configured to operate in either
		half or full duplex mode. The values are:
			halfDuplex(1)...half duplex mode
			fullDuplex(2)...full duplex mode
		The read-back channel status from hardware are:
            none(0).........link down or port disabled.
			halfDuplex(1)...half duplex mode
			fullDuplex(2)...full duplex mode
		
		The port media type (expansion or regular)
		and port link type (trunk or feeder) determine
		value of this object.
		The port can not set to half duplex mode
		if the port connect mode is m200e(4).
		However, the value of this parameter may be
		automatically set whenever the expansion port
		is connected (e.g. cascade connecting device)."
	::= { snSwIfInfoEntry 6 }

snSwIfInfoSpeed OBJECT-TYPE
	SYNTAX  INTEGER {
				none(0),
				sAutoSense(1),
				s10M(2),
				s100M(3),
				s1G(4),
				s1GM(5),
				s155M(6),
				s10G(7)
			}
	ACCESS  read-write
	STATUS  mandatory
	DESCRIPTION     
		"The speed configuration for a port. The values are:
          none(0)..........link down or no traffic.
		  sAutoSense(1)....Auto-sensing 10 or 100Mbits.
		  s10M(2)..........10Mbits per second.
		  s100M(3).........100Mbits per second.
		  s1G(4)...........1Gbits per second.
		  s1GM(5)..........1Gbits per second master.
		  s155M(6).........155Mbits per second (ATM) (for expansion board only).
		  s10G(7)..........10Gbits per second.

         The read-back hardware status are the following:
          none(0)..........link down or no traffic.
		  s10M(2)..........10Mbits per second.
		  s100M(3).........100Mbits per second.
		  s1G(4)...........1Gbits per second.
		  s1GM(5)..........1Gbits per second master.
		  s155M(6).........155Mbits per second (ATM) (for expansion board only).
		  s10G(7)..........10Gbits per second.

		The port media type (expansion or regular)
		and port link type (trunk or feeder) determine
		whether this object can be written and the valid
		values.
		It is not allowed to change speed for trunks ports.
		For expansion ports, all of the above speed 
		can be set.
		However, the value of this parameter may be
		automatically set whenever the expansion port
		is connected (e.g. cascade connecting device)."
	::= { snSwIfInfoEntry 7 }

snSwIfInfoMediaType OBJECT-TYPE
	SYNTAX  INTEGER {
				other(1),
				m100BaseTX(2),
				m100BaseFX(3),
				m1000BaseFX(4),
				mT3(5),
				m155ATM(6),
				m1000BaseTX(7),
				m622ATM(8),
				m155POS(9),
				m622POS(10),
				m2488POS(11),
				m10000BaseFX(12)
			}
	ACCESS  read-only
	STATUS  mandatory
	DESCRIPTION 
		"The media type for the port. The
		values are:
		  other(1).........other or unknown media.
		  m100BaseTX(2)....100Mbits per second copper.
		  m100BaseFX(3)....100Mbits per second fiber.
		  m1000BaseFX(4)...1Gbits per second fiber.
		  mT3(5)...........45Mbits per second (T3).
		  m155ATM(6).......155Mbits per second (ATM).
		  m1000BaseTX(7)...1Gbits per second copper.
		  m622ATM(8).......622Mbits per second (ATM).
		  m155POS(9).......155Mbits per second (POS).
		  m622POS(10)......622Mbits per second (POS).
		  m2488POS(11).....2488Mbits per second (POS).
		  m10000BaseFX(12).10Gbits per second fiber."
	::= { snSwIfInfoEntry 8 }

snSwIfInfoConnectorType OBJECT-TYPE
	SYNTAX  INTEGER {
				other(1),
				copper(2),
				fiber(3)
			}
	ACCESS  read-only
	STATUS  mandatory
	DESCRIPTION 
		"The type of connector that the port offers.
		 The values are:
		  other(1)...........other or unknown connector
		  copper(2)..........Copper connector
		  fiber(3)...........Fiber connector
		 This describes the physical connector type"
	::= { snSwIfInfoEntry 9 }

snSwIfInfoAdminStatus OBJECT-TYPE
    SYNTAX  INTEGER {
				up(1),       -- ready to pass packets
				down(2),
				testing(3)   -- in some test mode
			}
    ACCESS  read-write
    STATUS  mandatory
    DESCRIPTION
		"The desired state of all ports.  The
	 	testing(3) state indicates that no operational
	 	packets can be passed. 
	 	(same as ifAdminStatus in MIB-II)"
    ::= { snSwIfInfoEntry 10 }

snSwIfInfoLinkStatus OBJECT-TYPE
    SYNTAX  INTEGER {
    			up(1),       -- ready to pass packets
    			down(2),
    			testing(3)   -- in some test mode
			}
    ACCESS  read-only
    STATUS  mandatory
    DESCRIPTION
        "The current operational state of the interface.
         The testing(3) state indicates that no operational
         packets can be passed. 
         (same as ifOperStatus in MIB-II)"
    ::= { snSwIfInfoEntry 11 }

snSwIfInfoPortQos OBJECT-TYPE
	SYNTAX  INTEGER {
				level0(0),
				level1(1),
				level2(2),
				level3(3),
				level4(4),
				level5(5),
				level6(6),
				level7(7)
			}
	ACCESS  read-write
	STATUS  mandatory
	DESCRIPTION
		"The Stand alone stackable switch Port Qos Priority values are:
		 low(0)   -- low prority
		 high(1) -- high prority.
		 The BigIron Port Qos Priority values are:
		level0(0), level1(1), level2(2), level3(3),
		level4(4), level5(5), level6(6), level7(7) "
	::= { snSwIfInfoEntry 12 }

snSwIfInfoPhysAddress OBJECT-TYPE
	SYNTAX  PhysAddress
	ACCESS  read-only
	STATUS  mandatory
	DESCRIPTION
		"The port physical address. The physical address 
		represents the switch port."
	::= { snSwIfInfoEntry 13 }

snSwIfLockAddressCount OBJECT-TYPE
     SYNTAX  INTEGER (0..2048)
     ACCESS  read-write
     STATUS  mandatory
     DESCRIPTION
	 	"The number of source MAC addresses are allowed
	 	for a port. Writing 0 to this object will allow
	 	any number of addresses."
    DEFVAL { 8 }
    ::= { snSwIfInfoEntry 14 }

snSwIfStpPortEnable OBJECT-TYPE
     SYNTAX  INTEGER {
				disabled(0),
				enabled(1)
             }
     ACCESS  read-write
     STATUS  mandatory
     DESCRIPTION
        "The enabled/disabled status of the port."
     REFERENCE
     	"IEEE 802.1D-1990: Section 4.5.5.2, dot1dStpPortEnable"
     ::= { snSwIfInfoEntry 15 }

snSwIfDhcpGateListId OBJECT-TYPE
	SYNTAX  INTEGER (0..32)
	ACCESS  read-write
	STATUS  mandatory
	DESCRIPTION
		"The ID for a DHCP gateway list entry relative 
		 to this switch port. 0 = unset or no assigned ID"
	::= { snSwIfInfoEntry 16 }

snSwIfName OBJECT-TYPE
	SYNTAX	DisplayString (SIZE(0..255))
	ACCESS	read-write
	STATUS	mandatory
	DESCRIPTION
		"Port Name string."
	::= { snSwIfInfoEntry 17 }

snSwIfDescr OBJECT-TYPE
    SYNTAX  DisplayString
    ACCESS  read-only
    STATUS  mandatory
    DESCRIPTION
    	"A textual string containing the slot/port information
    	about the interface."
    ::= { snSwIfInfoEntry 18 }

snSwIfInfoAutoNegotiate OBJECT-TYPE
	SYNTAX  INTEGER {
				disabled(0),
				enabled(1),
				negFullAuto(2),
				global(3),
				other(4)
			}
	ACCESS  read-write
	STATUS  mandatory
	DESCRIPTION
		"This feature only applies to Gigabit Ethernet ports. If set to
		disable(0), port will be put to non-negotiation mode. If set to
		enable(1), port will start auto-negotiation indefinitely until
		succeed. If set to negFullAuto(2), the port will start with auto-
		negotiation, if the negotiation failed, then it will automatically
		switch to non-negotiation mode. Stackable products (except TurboIron
		8) Gigabit Ethernet ports do not support negFullAuto(2). If set
		to global(3), port negotiation mode follows the value of
		snSwGlobalAutoNegotiate. Non-Gigabit Ethernet port returns
		the value other(4)."
    DEFVAL { global }
	::= { snSwIfInfoEntry 19 }

snSwIfInfoFlowControl OBJECT-TYPE
	SYNTAX  INTEGER {
				disabled(0),
				enabled(1)
			}
	ACCESS  read-write
	STATUS  mandatory
	DESCRIPTION
		"Enable/Disbale port flow control."
    DEFVAL { enabled }
	::= { snSwIfInfoEntry 20 }

snSwIfInfoGigType OBJECT-TYPE
	SYNTAX  INTEGER {
				m1000BaseSX(0),
				m1000BaseLX(1),
				m1000BaseLH(2),
				m1000BaseLHA(3),
				m1000BaseLHB(4),
				m1000BaseTX(5),
				m10000BaseSR(6),
				m10000BaseLR(7),
				m10000BaseER(8),
				sfpCWDM1470nm80Km(9),
				sfpCWDM1490nm80Km(10),
				sfpCWDM1510nm80Km(11),
				sfpCWDM1530nm80Km(12),
				sfpCWDM1550nm80Km(13),
				sfpCWDM1570nm80Km(14),
				sfpCWDM1590nm80Km(15),
				sfpCWDM1610nm80Km(16),
				sfpCWDM1470nm100Km(17),
				sfpCWDM1490nm100Km(18),
				sfpCWDM1510nm100Km(19),
				sfpCWDM1530nm100Km(20),
				sfpCWDM1550nm100Km(21),
				sfpCWDM1570nm100Km(22),
				sfpCWDM1590nm100Km(23),
				sfpCWDM1610nm100Km(24),
				m1000BaseLHX(25),
				notApplicable(255)
			}
	ACCESS  read-only
	STATUS  mandatory
	DESCRIPTION 
		"The media type for the port. The
		values are:
		  m1000BaseSX(0)....1Gbits per second fiber, with a short wavelength transceiver.
		  m1000BaseLX(1)....1Gbits per second fiber, with a long wavelength transceiver (3km).
		  m1000BaseLH(2)....1Gbits per second fiber, with a special wavelength transceiver (50km).
		  m1000BaseLHA(3)....1Gbits per second fiber, with a special wavelength transceiver (70km).
		  m1000BaseLHB(4)....1Gbits per second fiber, with a special wavelength transceiver (150km).
		  m1000BaseTX(5)....1Gbits per second copper (100meter).
		  m10000BaseSR(6)....10Gbits per second fiber, with a short range wavelength transceiver (100m).
		  m10000BaseLR(7)....10Gbits per second fiber, with a long range wavelength transceiver (10km).
		  m10000BaseER(8)....10Gbits per second fiber, with a extended range wavelength transceiver (40km).
		  sfpCWDM1470nm80Km(9)....1Gbits per second CWDM fiber, with a wavelength 1470nm, reach 80 kms.
		  sfpCWDM1490nm80Km(10)....1Gbits per second CWDM fiber, with a wavelength 1490nm, reach 80 kms.
		  sfpCWDM1510nm80Km(11)....1Gbits per second CWDM fiber, with a wavelength 1510nm, reach 80 kms.
		  sfpCWDM1530nm80Km(12)....1Gbits per second CWDM fiber, with a wavelength 1530nm, reach 80 kms.
		  sfpCWDM1550nm80Km(13)....1Gbits per second CWDM fiber, with a wavelength 1550nm, reach 80 kms.
		  sfpCWDM1570nm80Km(14)....1Gbits per second CWDM fiber, with a wavelength 1570nm, reach 80 kms.
		  sfpCWDM1590nm80Km(15)....1Gbits per second CWDM fiber, with a wavelength 1590nm, reach 80 kms.
		  sfpCWDM1610nm80Km(16)....1Gbits per second CWDM fiber, with a wavelength 1610nm, reach 80 kms.
		  sfpCWDM1470nm100Km(17)....1Gbits per second CWDM fiber, with a wavelength 1470nm, reach 100 kms.
		  sfpCWDM1490nm100Km(18)....1Gbits per second CWDM fiber, with a wavelength 1490nm, reach 100 kms.
		  sfpCWDM1510nm100Km(19)....1Gbits per second CWDM fiber, with a wavelength 1510nm, reach 100 kms.
		  sfpCWDM1530nm100Km(20)....1Gbits per second CWDM fiber, with a wavelength 1530nm, reach 100 kms.
		  sfpCWDM1550nm100Km(21)....1Gbits per second CWDM fiber, with a wavelength 1550nm, reach 100 kms.
		  sfpCWDM1570nm100Km(22)....1Gbits per second CWDM fiber, with a wavelength 1570nm, reach 100 kms.
		  sfpCWDM1590nm100Km(23)....1Gbits per second CWDM fiber, with a wavelength 1590nm, reach 100 kms.
		  sfpCWDM1610nm100Km(24)....1Gbits per second CWDM fiber, with a wavelength 1610nm, reach 100 kms.
		  m1000BaseLHX(25)...1Gbits per second fiber, with a special wavelength transceiver (150km).
		  notApplicable(255)....a non-gigabit port."
	::= { snSwIfInfoEntry 21 }

snSwIfFastSpanPortEnable OBJECT-TYPE
     SYNTAX  INTEGER {
				disabled(0),
				enabled(1)
             }
     ACCESS  read-write
     STATUS  mandatory
     DESCRIPTION
        "The enabled/disabled fast span port status of the port."
     ::= { snSwIfInfoEntry 22 }

snSwIfFastSpanUplinkEnable OBJECT-TYPE
     SYNTAX  INTEGER {
				disabled(0),
				enabled(1)
             }
     ACCESS  read-write
     STATUS  mandatory
     DESCRIPTION
        "The enabled/disabled fast span uplink status of the port."
     ::= { snSwIfInfoEntry 23 }

snSwIfVlanId OBJECT-TYPE
     SYNTAX  INTEGER (0..4095)
     ACCESS  read-write
     STATUS  mandatory
     DESCRIPTION
        "The ID of a VLAN of which this port is a member. Port must
        be untagged. For tagged port which belongs to multiple
        VLANs, this object return 0 which is an invalid VLAN ID
        value."
     ::= { snSwIfInfoEntry 24 }

snSwIfRouteOnly OBJECT-TYPE
     SYNTAX INTEGER {
				disabled(0),
				enabled(1)
			}
     ACCESS  read-write
     STATUS  mandatory
     DESCRIPTION
        "Enable/Disable L2 switching of a routing switch port.
		By default, the routing switch performs routing first.
		If routing failed, it performs switching. Enable route
		only instrcuts the routing switch to perform routing
		only. For a L2 switching only product, reading this
		object always return 'disabled', writing 'enabled' to
		this object takes no effect."
     DEFVAL { disabled }
     ::= { snSwIfInfoEntry 25 }

snSwIfPresent OBJECT-TYPE
     SYNTAX  INTEGER {
				false(0),
				true(1)
             }
     ACCESS  read-only
     STATUS  mandatory
     DESCRIPTION
        "Indicate if the port is absent or present.
		 This object only valid for M4 module."
     ::= { snSwIfInfoEntry 26 }

snSwIfGBICStatus OBJECT-TYPE
     SYNTAX  INTEGER {
				gbic(1),
				miniGBIC(2),
				empty(3),
				other(4)
             }
     ACCESS  read-only
     STATUS  mandatory
     DESCRIPTION
        "Indicate if the gig port has GBICs on them.
		 If set to  GBIC(1), it means that the port is GBIC.
		 If set to  miniGBIC(2), it means that the port miniGBIC.
		 If set to empty(3), it means that the GBIC is missing.
		 Value other(4) means that the port not a removable gig port.
		 "
     ::= { snSwIfInfoEntry 27 }

snSwIfLoadInterval OBJECT-TYPE
     SYNTAX  INTEGER (30..300)
     ACCESS  read-write
     STATUS  mandatory
     DESCRIPTION
        "The time in seconds for which average port utilization should be carried out.
        The value should be incremental of 30 seconds, between the ranges specified."
     DEFVAL { 300 }
     ::= { snSwIfInfoEntry 28 }

snSwIfStatsInFrames OBJECT-TYPE
    SYNTAX  Counter32
    ACCESS  read-only
    STATUS  mandatory
    DESCRIPTION
    	"The total number of packets received on the interface."
    ::= { snSwIfInfoEntry 29 }

snSwIfStatsOutFrames OBJECT-TYPE
    SYNTAX  Counter32
    ACCESS  read-only
    STATUS  mandatory
    DESCRIPTION
    	"The total number of packets transmitted out of the interface."
    ::= { snSwIfInfoEntry 30 }

snSwIfStatsAlignErrors   OBJECT-TYPE
     SYNTAX     Counter32
     ACCESS     read-only
     STATUS     mandatory
     DESCRIPTION
		"dot3StatsAlignmentErrors : A count of frames 
		received on a particular interface that are 
		not an integral number of octets in length 
		and do not pass the FCS check.

		The count represented by an instance of this
		object is incremented when the alignmentError
		status is returned by the MAC service to the
		LLC (or other MAC user). Received frames for
		which multiple error conditions obtain are,
		according to the conventions of IEEE 802.3
		Layer Management, counted exclusively according
		to the error status presented to the LLC."
    ::= { snSwIfInfoEntry 31 }

snSwIfStatsFCSErrors   OBJECT-TYPE
     SYNTAX      Counter32
     ACCESS      read-only
     STATUS      mandatory
     DESCRIPTION
	 	"dot3StatsFCSErrors : A count of frames received 
	  	on a particular interface that are an integral 
	  	number of octets in length but do not pass the 
	  	FCS check.

	  	The count represented by an instance of this
	  	object is incremented when the frameCheckError
	  	status is returned by the MAC service to the
	  	LLC (or other MAC user). Received frames for
	  	which multiple error conditions obtain are,
	  	according to the conventions of IEEE 802.3
	  	Layer Management, counted exclusively according
	  	to the error status presented to the LLC."
    ::= { snSwIfInfoEntry 32 }

snSwIfStatsMultiColliFrames   OBJECT-TYPE
     SYNTAX      Counter32
     ACCESS      read-only
     STATUS      mandatory
     DESCRIPTION
	 	"dot3StatsMultipleCollisionFrames : 
	  	A count of successfully transmitted frames on
	  	a particular interface for which transmission
	  	is inhibited by more than one collision.

	  	A frame that is counted by an instance of this
	  	object is also counted by the corresponding
	  	instance of either the ifOutUcastPkts,
	  	ifOutMulticastPkts, or ifOutBroadcastPkts,
	  	and is not counted by the corresponding
	  	instance of the dot3StatsSingleCollisionFrames
	  	object."
    ::= { snSwIfInfoEntry 33 }

snSwIfStatsTxColliFrames   OBJECT-TYPE
     SYNTAX      Counter32
     ACCESS      read-only
     STATUS      mandatory
     DESCRIPTION
	 	"A count of successfully transmitted frames on
	  	a particular interface for which transmission
	  	is inhibited by more than one collision.

	  	A frame that is counted by a combination of
		both dot3StatsSingleCollisionFrames and
		dot3StatsMultipleCollisionFrames objects."
    ::= { snSwIfInfoEntry 34 }

snSwIfStatsRxColliFrames   OBJECT-TYPE
     SYNTAX      Counter32
     ACCESS      read-only
     STATUS      mandatory
     DESCRIPTION
	 	"A count of successfully received frames on
	  	a particular interface for which transmission
	  	is inhibited by more than one collision.  This
	  	object is not specified in dot3 but it has the
	  	same functionarity as snSwIfStatsTxColliFrames."
    ::= { snSwIfInfoEntry 35 }

snSwIfStatsFrameTooLongs   OBJECT-TYPE
     SYNTAX    Counter32
     ACCESS    read-only
     STATUS    mandatory
     DESCRIPTION
	 	"dot3StatsFrameTooLongs : A count of frames 
	  	received on a particular interface that 
	  	exceed the maximum permitted frame size.

	  	The count represented by an instance of this
	  	object is incremented when the frameTooLong
	  	status is returned by the MAC service to the
	  	LLC (or other MAC user). Received frames for
	  	which multiple error conditions obtain are,
	  	according to the conventions of IEEE 802.3
	  	Layer Management, counted exclusively according
	  	to the error status presented to the LLC."
    ::= { snSwIfInfoEntry 36 }
    
snSwIfStatsFrameTooShorts   OBJECT-TYPE
     SYNTAX    Counter32
     ACCESS    read-only
     STATUS    mandatory
     DESCRIPTION
	 	" A count of frames received on a particular 
	 	interface that below the minimum permitted 
	 	frame size."
    ::= { snSwIfInfoEntry 37 }
    
snSwIfStatsInBcastFrames OBJECT-TYPE
    SYNTAX  Counter32
    ACCESS  read-only
    STATUS  mandatory
    DESCRIPTION
    	"The total number of broadcast packets received on the interface."
    ::= { snSwIfInfoEntry 38 }

snSwIfStatsOutBcastFrames OBJECT-TYPE
    SYNTAX  Counter32
    ACCESS  read-only
    STATUS  mandatory
    DESCRIPTION
    	"The total number of broadcast packets transmitted out of the interface."
    ::= { snSwIfInfoEntry 39 }

snSwIfStatsInMcastFrames OBJECT-TYPE
    SYNTAX  Counter32
    ACCESS  read-only
    STATUS  mandatory
    DESCRIPTION
    	"The total number of multicast packets received on the interface."
    ::= { snSwIfInfoEntry 40 }

snSwIfStatsOutMcastFrames OBJECT-TYPE
    SYNTAX  Counter32
    ACCESS  read-only
    STATUS  mandatory
    DESCRIPTION
    	"The total number of multicast packets transmitted out of the interface."
    ::= { snSwIfInfoEntry 41 }

snSwIfStatsInDiscard OBJECT-TYPE
    SYNTAX  Counter32
    ACCESS  read-only
    STATUS  mandatory
    DESCRIPTION
        "The number of inbound packets which were chosen
         to be discarded even though no errors had been
         detected to prevent their being deliverable to a
         higher-layer protocol.  One possible reason for
         discarding such a packet could be to free up
         buffer space."
    ::= { snSwIfInfoEntry 42 }

snSwIfStatsOutDiscard OBJECT-TYPE
    SYNTAX  Counter32
    ACCESS  read-only
    STATUS  mandatory
    DESCRIPTION
        "The number of outbound packets which were chosen
         to be discarded even though no errors had been
         detected to prevent their being transmitted.  One
         possible reason for discarding such a packet could
         be to free up buffer space."
    ::= { snSwIfInfoEntry 43 }

snSwIfStatsMacStations OBJECT-TYPE
    SYNTAX  INTEGER
    ACCESS  read-only
    STATUS  mandatory
    DESCRIPTION
    	"The total number of MAC Stations connected to the interface."
    ::= { snSwIfInfoEntry 44 }

snSwIfStatsLinkChange OBJECT-TYPE
    SYNTAX  Counter32
    ACCESS  read-only
    STATUS  mandatory
    DESCRIPTION
    	"The total number of link state change of the interface."
    ::= { snSwIfInfoEntry 45 }

snSwIfInOctets OBJECT-TYPE
    SYNTAX  Counter64
    ACCESS  read-only
    STATUS  mandatory
    DESCRIPTION
    	"The total number of octets received on the interface,
    	including framing characters. This object is a 64-bit
		counter of the ifInOctets object, defined in RFC 1213.
		The octet string is in big-endian byte order."
    ::= { snSwIfInfoEntry 46 }

snSwIfOutOctets OBJECT-TYPE
    SYNTAX  Counter64
    ACCESS  read-only
    STATUS  mandatory
    DESCRIPTION
    	"The total number of octets transmitted out of the interface,
    	including framing characters. This object is a 64-bit
		counter of the ifOutOctets object, defined in RFC 1213.
		The octet string is in big-endian byte order."
    ::= { snSwIfInfoEntry 47 }

snSwIfStatsInBitsPerSec OBJECT-TYPE
    SYNTAX  Gauge32
    ACCESS  read-only
    STATUS  mandatory
    DESCRIPTION
    	"The number of bits per second received on the interface
    	over a 5 minutes interval."
    ::= { snSwIfInfoEntry 48 }

snSwIfStatsOutBitsPerSec OBJECT-TYPE
    SYNTAX  Gauge32
    ACCESS  read-only
    STATUS  mandatory
    DESCRIPTION
    	"The number of bits per second transmitted out of the interface
    	over a 5 minutes interval."
    ::= { snSwIfInfoEntry 49 }

snSwIfStatsInPktsPerSec OBJECT-TYPE
    SYNTAX  Gauge32
    ACCESS  read-only
    STATUS  mandatory
    DESCRIPTION
    	"The number of packets per second received on the interface
    	over a 5 minutes interval."
    ::= { snSwIfInfoEntry 50 }

snSwIfStatsOutPktsPerSec OBJECT-TYPE
    SYNTAX  Gauge32
    ACCESS  read-only
    STATUS  mandatory
    DESCRIPTION
    	"The number of packets per second transmitted out of the interface
    	over a 5 minutes interval."
    ::= { snSwIfInfoEntry 51 }

snSwIfStatsInUtilization OBJECT-TYPE
    SYNTAX  INTEGER (0..10000)
    ACCESS  read-only
    STATUS  mandatory
    DESCRIPTION
    	"The input network utilization in hundredths of a percent
    	over a 5 minutes interval."
    ::= { snSwIfInfoEntry 52 }

snSwIfStatsOutUtilization OBJECT-TYPE
    SYNTAX  INTEGER (0..10000)
    ACCESS  read-only
    STATUS  mandatory
    DESCRIPTION
    	"The output network utilization in hundredths of a percent
    	over a 5 minutes interval."
    ::= { snSwIfInfoEntry 53 }
    
snSwIfStatsInKiloBitsPerSec OBJECT-TYPE
    SYNTAX  Unsigned32
    ACCESS  read-only
    STATUS  mandatory
    DESCRIPTION
    	"Bit rate in kilobits per second received on the 10G and
    	 faster interface over a 5 minutes interval."
    ::= { snSwIfInfoEntry 54 }

snSwIfStatsOutKiloBitsPerSec OBJECT-TYPE
    SYNTAX  Unsigned32
    ACCESS  read-only
    STATUS  mandatory
    DESCRIPTION
    	"Bit rate in kilobits per second transmitted out of the 10G
    	 and faster interface over a 5 minutes interval."
    ::= { snSwIfInfoEntry 55 }

snSwIfStatsInJumboFrames OBJECT-TYPE
    SYNTAX  Counter64
    ACCESS  read-only
    STATUS  mandatory
    DESCRIPTION
    	"The total number of jumbo packets received on the interface."
    ::= { snSwIfInfoEntry 56 }

snSwIfStatsOutJumboFrames OBJECT-TYPE
    SYNTAX  Counter64
    ACCESS  read-only
    STATUS  mandatory
    DESCRIPTION
    	"The total number of jumbo packets transmitted out of the interface."
    ::= { snSwIfInfoEntry 57 }

snSwIfInfoMirrorMode OBJECT-TYPE
     SYNTAX  INTEGER {
               disable(0),
               enable(1)
             }
     ACCESS  read-write
     STATUS  mandatory
     DESCRIPTION
             "Enable/disable mirror on this port."
     ::= { snSwIfInfoEntry 58 }

-- Interface ID Registration Group

snInterfaceId      OBJECT IDENTIFIER ::= { snSwPortInfo 2 }

-- Interface ID to ifIndex Lookup Table
-- Given an interface ID, this table returns the ifIndex value.
-- 
-- Note: This table does not behave like most SNMP tables.  It does not
-- support GetNext.  If you try to walk the table using GetNext, no rows
-- will be returned.  The contents of the table can only be accessed
-- using Get operations.  The table is useful for mapping a known
-- interface to the corresponding ifIndex value.

snInterfaceLookupTable OBJECT-TYPE
	SYNTAX  SEQUENCE OF SnInterfaceLookupEntry
	ACCESS  not-accessible
	STATUS  mandatory
	DESCRIPTION
		""
	::= { snSwPortInfo 3 }

snInterfaceLookupEntry OBJECT-TYPE
	SYNTAX  SnInterfaceLookupEntry
	ACCESS  not-accessible
	STATUS  mandatory
	DESCRIPTION
		""
	INDEX { snInterfaceLookupInterfaceId }
	::= { snInterfaceLookupTable 1 }

SnInterfaceLookupEntry ::= SEQUENCE {
	snInterfaceLookupInterfaceId
		InterfaceId,
	snInterfaceLookupIfIndex
	    INTEGER
	}

snInterfaceLookupInterfaceId OBJECT-TYPE
     SYNTAX  InterfaceId
     ACCESS  read-only
     STATUS  mandatory
     DESCRIPTION
        ""
     ::= { snInterfaceLookupEntry 1 }

snInterfaceLookupIfIndex OBJECT-TYPE
     SYNTAX  INTEGER
     ACCESS  read-only
     STATUS  mandatory
     DESCRIPTION
        ""
     ::= { snInterfaceLookupEntry 2 }


-- ifIndex to Interface ID Lookup Table
-- Given an ifIndex, this table returns the interface ID value.

snIfIndexLookupTable OBJECT-TYPE
	SYNTAX  SEQUENCE OF SnIfIndexLookupEntry
	ACCESS  not-accessible
	STATUS  mandatory
	DESCRIPTION
		""
	::= { snSwPortInfo 4 }

snIfIndexLookupEntry OBJECT-TYPE
	SYNTAX  SnIfIndexLookupEntry
	ACCESS  not-accessible
	STATUS  mandatory
	DESCRIPTION
		""
	INDEX { snIfIndexLookupIfIndex }
	::= { snIfIndexLookupTable 1 }

SnIfIndexLookupEntry ::= SEQUENCE {
	snIfIndexLookupIfIndex
	    INTEGER,
	snIfIndexLookupInterfaceId
		InterfaceId
	}

snIfIndexLookupIfIndex OBJECT-TYPE
     SYNTAX  INTEGER
     ACCESS  read-only
     STATUS  mandatory
     DESCRIPTION
        ""
     ::= { snIfIndexLookupEntry 1 }

snIfIndexLookupInterfaceId OBJECT-TYPE
     SYNTAX  InterfaceId
     ACCESS  read-only
     STATUS  mandatory
     DESCRIPTION
        ""
     ::= { snIfIndexLookupEntry 2 }


--      Forwarding Database Group
--
-- This group contains information relevant to 
-- the forwarding database in the system.



-- The Forward Database Static Table Information
--
-- This table contains all MAC addresses in the system. Static 
-- stations may be configured.


snFdbTable OBJECT-TYPE
	SYNTAX  SEQUENCE OF SnFdbEntry
	ACCESS  not-accessible
	STATUS  mandatory
	DESCRIPTION
		"This table contains snFdb information for each station
		known to the system, one entry per station." 
	::= { snFdbInfo 1 }

snFdbEntry OBJECT-TYPE
	SYNTAX  SnFdbEntry
	ACCESS  not-accessible
	STATUS  mandatory
	DESCRIPTION
		"Each entry represents the information of a static MAC station." 
	INDEX   { 
		snFdbStationIndex
	}
	::= { snFdbTable 1 }


SnFdbEntry ::= SEQUENCE {
    snFdbStationIndex
		INTEGER,
    snFdbStationAddr
	    PhysAddress,
	snFdbStationPort
		INTEGER,
	snFdbVLanId
		INTEGER,
	snFdbStationQos
		INTEGER,
	snFdbStationType
		INTEGER,
	snFdbRowStatus
		INTEGER
	}

snFdbStationIndex OBJECT-TYPE
	SYNTAX  INTEGER (1..256)
	ACCESS  read-only
	STATUS  mandatory
	DESCRIPTION
		"The FDB Station index to the Fdb Station Table."
	::= { snFdbEntry 1 }

snFdbStationAddr OBJECT-TYPE
	SYNTAX  PhysAddress
	ACCESS  read-write
	STATUS  mandatory
	DESCRIPTION
		"The snFdbs physical address. The physical address 
		represents a MAC Station."
	::= { snFdbEntry 2 }


snFdbStationPort OBJECT-TYPE
	SYNTAX  INTEGER
	ACCESS  read-write
	STATUS  mandatory
	DESCRIPTION
		"Station slot/port number. 
		 The bit 0 to bit 7: port number. 
		 The bit 8 to bit 11: slot number (slot for chassis only)."
	::= { snFdbEntry 3 }


snFdbVLanId OBJECT-TYPE
	SYNTAX  INTEGER (1..65535)
	ACCESS  read-write
	STATUS  mandatory
	DESCRIPTION
		"The Station VLan ID."
	::= { snFdbEntry 4 }

snFdbStationQos OBJECT-TYPE
	SYNTAX  INTEGER {
		level0(0),
		level1(1),
		level2(2),
		level3(3),
		level4(4),
		level5(5),
		level6(6),
		level7(7)
		}
	ACCESS  read-write
	STATUS  mandatory
	DESCRIPTION
		"The Stand alone stackable station Qos Priority values are:
		 low(0)   -- low prority
		 high(1) -- high prority.
		 The BigIron switch station Priority values are:
		level0(0), level1(1), level2(2), level3(3),
		level4(4), level5(5), level6(6), level7(7) "
	::= { snFdbEntry 5 }

snFdbStationType OBJECT-TYPE
	SYNTAX  INTEGER {
		notSupported(0),
		host(1),
		router(2)
		}
	ACCESS  read-write
	STATUS  mandatory
	DESCRIPTION
		"The station type values are:
		 notSupported    -- a read value only : this product does not 
		                    support MultiLayer Switching.
		 host    -- any MAC station.
		 router  -- a router-typed station."
	::= { snFdbEntry 6 }

snFdbRowStatus OBJECT-TYPE
	SYNTAX  INTEGER {
		other(1),
		valid(2),
		delete(3),
		create(4)
		}
	ACCESS  read-write
	STATUS  mandatory
	DESCRIPTION
		"This object is used to create and
		delete row in the table and control
		if they are used. The values
		that can be written are:
		  delete(3)...deletes the row
		  create(4)...creates a new row

		If the row exists, then a SET with
		value of create(4) returns error
		'badValue'. Deleted rows go away
		immediately. The following values
		can be returned on reads:
		  noSuch(0)...no such row
		  other(1)....some other case
		  valid(2)....the row exists and is valid"
	::= { snFdbEntry 7 }


-- Port STP Configuration Group
-- snPortStpTable was deprecated. It has been replaced by snIfStpTable.


snPortStpTable OBJECT-TYPE
	SYNTAX  SEQUENCE OF SnPortStpEntry
	ACCESS  not-accessible
	STATUS  deprecated
	DESCRIPTION
		"A specific snPortStpTable consists of a number of 
		 switch ports. This table only exists if only if
		 snVLanByPortCfgTable exists and snVLanByPortCfgStpMode is
		 enabled for each VLAN."
	::= { snPortStpInfo 1 }

snPortStpEntry OBJECT-TYPE
	SYNTAX  SnPortStpEntry
	ACCESS  not-accessible
	STATUS  deprecated
	DESCRIPTION
		"An entry in the snPortStpTable indicates the 
		 configuration on a specified port. A SNMP SET PDU 
		 for a row of the snPortStpTable requires the entired 
		 sequence of the MIB Objects in each 
		 snPortStpEntry stored in one PDU.  Otherwise, 
	 	 GENERR return-value will be returned."
	INDEX   { 
			snPortStpVLanId,	
			snPortStpPortNum
	}
	::= { snPortStpTable 1 }

SnPortStpEntry ::= SEQUENCE {
	snPortStpVLanId
		INTEGER,
	snPortStpPortNum
		INTEGER,
	snPortStpPortPriority
		INTEGER,
	snPortStpPathCost 
		INTEGER,
    snPortStpOperState
		INTEGER,
    snPortStpPortEnable
        INTEGER,
    snPortStpPortForwardTransitions
        Counter,
    snPortStpPortState
        INTEGER,
    snPortStpPortDesignatedCost
        INTEGER,
    snPortStpPortDesignatedRoot
        BridgeId,
    snPortStpPortDesignatedBridge
        BridgeId,
    snPortStpPortDesignatedPort
        OCTET STRING,
    snPortStpPortAdminRstp
        INTEGER,
    snPortStpPortProtocolMigration
        INTEGER,
    snPortStpPortAdminEdgePort
        INTEGER,
    snPortStpPortAdminPointToPoint
        INTEGER
	}

snPortStpVLanId OBJECT-TYPE
	SYNTAX  INTEGER (1..65535)
	ACCESS  read-only
	STATUS  deprecated
	DESCRIPTION
		"The VLAN ID of the VLAN switch community." 
	::= { snPortStpEntry 1 }

snPortStpPortNum OBJECT-TYPE
	SYNTAX  INTEGER
	ACCESS  read-only
	STATUS  deprecated
	DESCRIPTION
		"The port number of the Switch. 
		 The bit 0 to bit 7: port number. 
		 The bit 8 to bit 11: slot number (slot for chassis only)."
	::= { snPortStpEntry 2 }

snPortStpPortPriority OBJECT-TYPE
	SYNTAX  INTEGER (8..255)
	ACCESS  read-write
	STATUS  deprecated
	DESCRIPTION
    "The value of the priority field which is
     contained in the first (in network byte order)
     octet of the (2 octet long) Port ID.  The other
     octet of the Port ID is given by the value of
     dot1dStpPort."
	::= { snPortStpEntry 3 }

snPortStpPathCost OBJECT-TYPE
    SYNTAX  INTEGER (0..65535)
    ACCESS  read-write
    STATUS  deprecated
    DESCRIPTION
	"dot1dStpPortPathCost : The contribution of this 
	 port to the path cost of paths towards the spanning 
	 tree root which include this port.  802.1D-1990 
	 recommends that the default value of this parameter 
	 be in inverse proportion to the speed of the 
	 attached LAN. Writing value zero to this object
	 sets path cost to a default value which automatically
	 changes according to port speed. Reading value zero
	 indicates an unknown path cost value because port
	 speed cannot be determined due to speed auto sense
	 in progress."
	::= { snPortStpEntry 4 }


snPortStpOperState OBJECT-TYPE
	SYNTAX  INTEGER {
		notActivated(0),             
		activated(1)
		}
	ACCESS  read-only
	STATUS  deprecated
	DESCRIPTION
		"By default, this mode is set to notActivated(0).
		 notActivated(0)...the Port STP entry is not activated and not in running mode.
		 activated(1)......the Port STP entry is activated and in running mode"  
	::= { snPortStpEntry 5 }

snPortStpPortEnable OBJECT-TYPE
    SYNTAX  INTEGER {
              enabled(1),
              disabled(2)
            }
    ACCESS  not-accessible
    STATUS  deprecated
    DESCRIPTION
    "The enabled/disabled status of the port."
	::= { snPortStpEntry 6 }

snPortStpPortForwardTransitions OBJECT-TYPE
    SYNTAX  Counter
    ACCESS  not-accessible
    STATUS  deprecated
    DESCRIPTION
    "The number of times this port has transitioned
     from the Learning state to the Forwarding state."
	::= { snPortStpEntry 7 }

snPortStpPortState OBJECT-TYPE
    SYNTAX  INTEGER {
              disabled(1),
              blocking(2),
              listening(3),
              learning(4),
              forwarding(5),
              broken(6),
              preforwarding(7)
            }
    ACCESS  read-only
    STATUS  deprecated
    DESCRIPTION
    "The port's current state as defined by
     application of the Spanning Tree Protocol.  This
     state controls what action a port takes on
     reception of a frame.  If the bridge has detected
     a port that is malfunctioning it will place that
     port into the broken(6) state.  For ports which
     are disabled (see dot1dStpPortEnable), this object
     will have a value of disabled(1)."
	::= { snPortStpEntry 8 }

snPortStpPortDesignatedCost OBJECT-TYPE
    SYNTAX  INTEGER
    ACCESS  read-only
    STATUS  deprecated
    DESCRIPTION
    "The path cost of the Designated Port of the
     segment connected to this port.  This value is
     compared to the Root Path Cost field in received
     bridge PDUs."
	::= { snPortStpEntry 9 }


snPortStpPortDesignatedRoot OBJECT-TYPE
    SYNTAX  BridgeId
    ACCESS  read-only
    STATUS  deprecated
    DESCRIPTION
    "The unique Bridge Identifier of the Bridge
     recorded as the Root in the Configuration BPDUs
     transmitted by the Designated Bridge for the
     segment to which the port is attached."
	::= { snPortStpEntry 10 }

snPortStpPortDesignatedBridge OBJECT-TYPE
    SYNTAX  BridgeId
    ACCESS  read-only
    STATUS  deprecated
    DESCRIPTION
    "The Bridge Identifier of the bridge which this
     port considers to be the Designated Bridge for
     this port's segment."
	::= { snPortStpEntry 11 }

snPortStpPortDesignatedPort OBJECT-TYPE
    SYNTAX  OCTET STRING (SIZE (2))
    ACCESS  read-only
    STATUS  deprecated
    DESCRIPTION
    "The Port Identifier of the port on the Designated
     Bridge for this port's segment."
	::= { snPortStpEntry 12 }

snPortStpPortAdminRstp OBJECT-TYPE
    SYNTAX  INTEGER {
              true(1),
              false(2)
            }
    ACCESS  read-write
    STATUS  deprecated
    DESCRIPTION
    "Enable or disable RSTP of a port which is a member of a VLAN.
    If the VLAN is not operating in RSTP, this object will return
    FALSE(2) and this object is not writable."
	::= { snPortStpEntry 13 }

snPortStpPortProtocolMigration OBJECT-TYPE
    SYNTAX  INTEGER {
              true(1),
              false(2)
            }
    ACCESS  read-write
    STATUS  deprecated
    DESCRIPTION
    "When operating in RSTP (version 2) mode, writing TRUE(1)
     to this object forces this port to transmit RSTP BPDUs.
     Any other operation on this object has no effect and
     it always returns FALSE(2) when read."
	::= { snPortStpEntry 14 }

snPortStpPortAdminEdgePort OBJECT-TYPE
    SYNTAX  INTEGER {
              true(1),
              false(2)
            }
    ACCESS  read-write
    STATUS  deprecated
    DESCRIPTION
    "The administrative value of the Edge Port parameter.  A
     value of TRUE(1) indicates that this port should be
     assumed as an edge-port and a value of FALSE(2) indicates
     that this port should be assumed as a non-edge-port."
	::= { snPortStpEntry 15 }

snPortStpPortAdminPointToPoint OBJECT-TYPE
    SYNTAX  INTEGER {
              true(1),
              false(2)
            }
    ACCESS  read-write
    STATUS  deprecated
    DESCRIPTION
    "The administrative point-to-point status of the LAN segment
     attached to this port.  A value of TRUE(1) indicates that
     this port should always be treated as if it is connected to
     a point-to-point link.  A value of FALSE(2) indicates
     that this port should be treated as having a shared media
     connection."
	::= { snPortStpEntry 16 }

-- Port STP Configuration Group
-- snIfStpTable is replacing snPortStpTable.
-- snIfStpPortNum is using ifIndex value to index snIfStpTable.


snIfStpTable OBJECT-TYPE
	SYNTAX  SEQUENCE OF SnIfStpEntry
	ACCESS  not-accessible
	STATUS  mandatory
	DESCRIPTION
		"A specific snIfStpTable consists of a number of 
		 switch ports. This table only exists if only if
		 snVLanByPortCfgTable exists and snVLanByPortCfgStpMode is
		 enabled for each VLAN."
	::= { snPortStpInfo 2 }

snIfStpEntry OBJECT-TYPE
	SYNTAX  SnIfStpEntry
	ACCESS  not-accessible
	STATUS  mandatory
	DESCRIPTION
		"An entry in the snIfStpTable indicates the 
		 configuration on a specified port. A SNMP SET PDU 
		 for a row of the snIfStpTable requires the entired 
		 sequence of the MIB Objects in each 
		 snIfStpEntry stored in one PDU.  Otherwise, 
	 	 GENERR return-value will be returned."
	INDEX   { 
			snIfStpVLanId,	
			snIfStpPortNum
	}
	::= { snIfStpTable 1 }

SnIfStpEntry ::= SEQUENCE {
	snIfStpVLanId
		INTEGER,
	snIfStpPortNum
		INTEGER,
	snIfStpPortPriority
		INTEGER,
	snIfStpCfgPathCost
		INTEGER,
    snIfStpOperState
		INTEGER,
    snIfStpPortState
        INTEGER,
    snIfStpPortDesignatedCost
        INTEGER,
    snIfStpPortDesignatedRoot
        BridgeId,
    snIfStpPortDesignatedBridge
        BridgeId,
    snIfStpPortDesignatedPort
        OCTET STRING,
    snIfStpPortAdminRstp
        INTEGER,
    snIfStpPortProtocolMigration
        INTEGER,
    snIfStpPortAdminEdgePort
        INTEGER,
    snIfStpPortAdminPointToPoint
        INTEGER,
    snIfStpOperPathCost
        INTEGER
	}

snIfStpVLanId OBJECT-TYPE
	SYNTAX  INTEGER (1..65535)
	ACCESS  read-only
	STATUS  mandatory
	DESCRIPTION
		"The VLAN ID of the VLAN switch community." 
	::= { snIfStpEntry 1 }

snIfStpPortNum OBJECT-TYPE
	SYNTAX  INTEGER
	ACCESS  read-only
	STATUS  mandatory
	DESCRIPTION
		"The port number of the Switch. It has the ifIndex value."
	::= { snIfStpEntry 2 }

snIfStpPortPriority OBJECT-TYPE
	SYNTAX  INTEGER (8..255)
	ACCESS  read-write
	STATUS  mandatory
	DESCRIPTION
    "The value of the priority field which is
     contained in the first (in network byte order)
     octet of the (2 octet long) Port ID.  The other
     octet of the Port ID is given by the value of
     dot1dStpPort."
	::= { snIfStpEntry 3 }

snIfStpCfgPathCost OBJECT-TYPE
    SYNTAX  INTEGER (0..200000000)
    ACCESS  read-write
    STATUS  mandatory
    DESCRIPTION
	"dot1dStpPortPathCost : The contribution of this 
	 port to the path cost of paths towards the spanning 
	 tree root which include this port.  802.1D-1990 
	 recommends that the default value of this parameter 
	 be in inverse proportion to the speed of the 
	 attached LAN. Writing value zero to this object
	 sets path cost to a default value which automatically
	 changes according to port speed."
	::= { snIfStpEntry 4 }


snIfStpOperState OBJECT-TYPE
	SYNTAX  INTEGER {
		notActivated(0),             
		activated(1)
		}
	ACCESS  read-only
	STATUS  mandatory
	DESCRIPTION
		"By default, this mode is set to notActivated(0).
		 notActivated(0)...the Port STP entry is not activated and not in running mode.
		 activated(1)......the Port STP entry is activated and in running mode"  
	::= { snIfStpEntry 5 }

snIfStpPortState OBJECT-TYPE
    SYNTAX  INTEGER {
              disabled(1),
              blocking(2),
              listening(3),
              learning(4),
              forwarding(5),
              broken(6),
              preforwarding(7)
            }
    ACCESS  read-only
    STATUS  mandatory
    DESCRIPTION
    "The port's current state as defined by
     application of the Spanning Tree Protocol.  This
     state controls what action a port takes on
     reception of a frame.  If the bridge has detected
     a port that is malfunctioning it will place that
     port into the broken(6) state.  For ports which
     are disabled (see dot1dStpPortEnable), this object
     will have a value of disabled(1)."
	::= { snIfStpEntry 8 }

snIfStpPortDesignatedCost OBJECT-TYPE
    SYNTAX  INTEGER
    ACCESS  read-only
    STATUS  mandatory
    DESCRIPTION
    "The path cost of the Designated Port of the
     segment connected to this port.  This value is
     compared to the Root Path Cost field in received
     bridge PDUs."
	::= { snIfStpEntry 9 }


snIfStpPortDesignatedRoot OBJECT-TYPE
    SYNTAX  BridgeId
    ACCESS  read-only
    STATUS  mandatory
    DESCRIPTION
    "The unique Bridge Identifier of the Bridge
     recorded as the Root in the Configuration BPDUs
     transmitted by the Designated Bridge for the
     segment to which the port is attached."
	::= { snIfStpEntry 10 }

snIfStpPortDesignatedBridge OBJECT-TYPE
    SYNTAX  BridgeId
    ACCESS  read-only
    STATUS  mandatory
    DESCRIPTION
    "The Bridge Identifier of the bridge which this
     port considers to be the Designated Bridge for
     this port's segment."
	::= { snIfStpEntry 11 }

snIfStpPortDesignatedPort OBJECT-TYPE
    SYNTAX  OCTET STRING (SIZE (2))
    ACCESS  read-only
    STATUS  mandatory
    DESCRIPTION
    "The Port Identifier of the port on the Designated
     Bridge for this port's segment."
	::= { snIfStpEntry 12 }

snIfStpPortAdminRstp OBJECT-TYPE
    SYNTAX  INTEGER {
              true(1),
              false(2)
            }
    ACCESS  read-write
    STATUS  mandatory
    DESCRIPTION
    "Enable or disable RSTP of a port which is a member of a VLAN.
    If the VLAN is not operating in RSTP, this object will return
    FALSE(2) and this object is not writable."
	::= { snIfStpEntry 13 }

snIfStpPortProtocolMigration OBJECT-TYPE
    SYNTAX  INTEGER {
              true(1),
              false(2)
            }
    ACCESS  read-write
    STATUS  mandatory
    DESCRIPTION
    "When operating in RSTP (version 2) mode, writing TRUE(1)
     to this object forces this port to transmit RSTP BPDUs.
     Any other operation on this object has no effect and
     it always returns FALSE(2) when read."
	::= { snIfStpEntry 14 }

snIfStpPortAdminEdgePort OBJECT-TYPE
    SYNTAX  INTEGER {
              true(1),
              false(2)
            }
    ACCESS  read-write
    STATUS  mandatory
    DESCRIPTION
    "The administrative value of the Edge Port parameter.  A
     value of TRUE(1) indicates that this port should be
     assumed as an edge-port and a value of FALSE(2) indicates
     that this port should be assumed as a non-edge-port."
	::= { snIfStpEntry 15 }

snIfStpPortAdminPointToPoint OBJECT-TYPE
    SYNTAX  INTEGER {
              true(1),
              false(2)
            }
    ACCESS  read-write
    STATUS  mandatory
    DESCRIPTION
    "The administrative point-to-point status of the LAN segment
     attached to this port.  A value of TRUE(1) indicates that
     this port should always be treated as if it is connected to
     a point-to-point link.  A value of FALSE(2) indicates
     that this port should be treated as having a shared media
     connection."
	::= { snIfStpEntry 16 }

snIfStpOperPathCost OBJECT-TYPE
    SYNTAX  INTEGER (0..200000000)
    ACCESS  read-only
    STATUS  mandatory
    DESCRIPTION
	"dot1dStpPortPathCost : The contribution of this 
	 port to the path cost of paths towards the spanning 
	 tree root which include this port.  802.1D-1990 
	 recommends that the default value of this parameter 
	 be in inverse proportion to the speed of the 
	 attached LAN. Reading value zero indicates an unknown
	 path cost value because port speed cannot be determined
	 due to speed auto sense in progress or port link is down."
	::= { snIfStpEntry 17 }


-- Trunk Port Configuration Group


snTrunkTable OBJECT-TYPE
	SYNTAX  SEQUENCE OF SnTrunkEntry
	ACCESS  not-accessible
	STATUS  mandatory
	DESCRIPTION
		"A specific snTrunkTable consists of a number of 
		 Trunk port-mask." 
	::= { snTrunkInfo 1 }

snTrunkEntry OBJECT-TYPE
	SYNTAX  SnTrunkEntry
	ACCESS  not-accessible
	STATUS  mandatory
	DESCRIPTION
		"An entry in the snTrunkTable indicates the 
		 configuration on a specified Trunk port membership." 
	INDEX   { 
		snTrunkIndex
	}
	::= { snTrunkTable 1 }

SnTrunkEntry ::= SEQUENCE {
	snTrunkIndex
		INTEGER,
	snTrunkPortMask
		PortMask,
	snTrunkType
		INTEGER
	}

snTrunkIndex OBJECT-TYPE
	SYNTAX  INTEGER
	ACCESS  read-only
	STATUS  mandatory
	DESCRIPTION
		"The number of the trunk entries can be configured.
		This can be 32*<slots> for Jetcore, and 16*<slots> for Ironcore."
	::= { snTrunkEntry 1 }


snTrunkPortMask OBJECT-TYPE
	SYNTAX  PortMask
	ACCESS  read-write
	STATUS  mandatory
	DESCRIPTION
		"Trunk membership of the Switch." 
	::= { snTrunkEntry 2 }


snTrunkType OBJECT-TYPE
	SYNTAX  INTEGER {
		switch(1),
	    server(2)
		}
	ACCESS  read-write
	STATUS  mandatory
	DESCRIPTION
		"The trunk connection type which specifies what
		device the trunk ports are connected to."
	::= { snTrunkEntry 3 }


-- Multi-slot Trunk Port Configuration Group


snMSTrunkTable OBJECT-TYPE
	SYNTAX  SEQUENCE OF SnMSTrunkEntry
	ACCESS  not-accessible
	STATUS  mandatory
	DESCRIPTION
		"A table contains the configuration of port members of
		multi-slot trunk groups."
	::= { snTrunkInfo 2 }

snMSTrunkEntry OBJECT-TYPE
	SYNTAX  SnMSTrunkEntry
	ACCESS  not-accessible
	STATUS  mandatory
	DESCRIPTION
		"An entry of the snMSTrunkTable."
	INDEX {snMSTrunkPortIndex}
	::= { snMSTrunkTable 1 }

SnMSTrunkEntry ::= SEQUENCE {
	snMSTrunkPortIndex
		INTEGER,
	snMSTrunkPortList
		OCTET STRING,
	snMSTrunkType
		INTEGER,
	snMSTrunkRowStatus
		INTEGER
	}

snMSTrunkPortIndex OBJECT-TYPE
	SYNTAX  INTEGER
	ACCESS  read-only
	STATUS  mandatory
	DESCRIPTION
		"The primary port of a trunk group. For module with Gig ports,
		primary port is port 1, 3, 5, 7. For module with 10/100 ports,
		primary port is port 1, 5, 9, 13, 17, 21."
	::= { snMSTrunkEntry 1 }


snMSTrunkPortList OBJECT-TYPE
	SYNTAX  OCTET STRING
	ACCESS  read-write
	STATUS  mandatory
	DESCRIPTION
		"A list of port indices which are the port membership
		of a trunk group. Each port index is a 16-bit integer
		in big endian order. The first port index must be the
		primary port index."
	::= { snMSTrunkEntry 2 }


snMSTrunkType OBJECT-TYPE
	SYNTAX  INTEGER {
		switch(1),
	    server(2)
		}
	ACCESS  read-write
	STATUS  mandatory
	DESCRIPTION
		"The trunk connection type which specifies what
		device the trunk ports are connected to."
	::= { snMSTrunkEntry 3 }


snMSTrunkRowStatus OBJECT-TYPE
	SYNTAX  INTEGER {
	    invalid(1),
	    valid(2),
	    delete(3),
	    create(4),
	    modify(5)
		}
	ACCESS  read-write
	STATUS  mandatory
	DESCRIPTION
		"To create or delete a table entry."
	::= { snMSTrunkEntry 4 }


-- Switch Configuration Summary Group


snSwSummaryMode OBJECT-TYPE
	SYNTAX  INTEGER {
		disabled(0),
		enabled(1)
		}
	ACCESS  read-write
	STATUS  mandatory
	DESCRIPTION
		"The Switch Group Configuration Summary is configured 
		 either enabled or disabled and the
		 default is disabled mode.
		 enabled(1)...........activate Switch Configuration Summary.
		 disabled(0)..........no Switch Configuration Summary."
	::= { snSwSummary 1 }


--- DHCP Gateway List Table


snDhcpGatewayListTable OBJECT-TYPE
	SYNTAX  SEQUENCE OF SnDhcpGatewayListEntry
	ACCESS  not-accessible
	STATUS  mandatory
	DESCRIPTION
		"A table of DHCP gateway list of addresses."
	::= { snDhcpGatewayListInfo 1 }

snDhcpGatewayListEntry             OBJECT-TYPE
	SYNTAX  SnDhcpGatewayListEntry
	ACCESS  not-accessible
	STATUS  mandatory
	DESCRIPTION
		"An entry in the IP Port Address table."
	INDEX   { snDhcpGatewayListId }
	::= { snDhcpGatewayListTable 1 }

SnDhcpGatewayListEntry ::= SEQUENCE {
	snDhcpGatewayListId
		INTEGER,
	snDhcpGatewayListAddrList
		OCTET STRING,
	snDhcpGatewayListRowStatus
		INTEGER
	}


snDhcpGatewayListId                 OBJECT-TYPE
	SYNTAX  INTEGER (1..32)
	ACCESS  read-only
	STATUS  mandatory
	DESCRIPTION
		"The ID for a DHCP gateway list entry."
	::= { snDhcpGatewayListEntry 1 }

snDhcpGatewayListAddrList          OBJECT-TYPE
	SYNTAX	OCTET STRING (SIZE(4..32))
	ACCESS  read-write
	STATUS  mandatory
	DESCRIPTION
		"The DHCP gateway address list for each DHCP gateway list ID.
		This list contains 1 to 8 IP addresses represented by octet string."
	::= { snDhcpGatewayListEntry 2 }

snDhcpGatewayListRowStatus OBJECT-TYPE
	SYNTAX  INTEGER {
		other(1),
		valid(2),
		delete(3),
		create(4)
		}
	ACCESS  read-write
	STATUS  mandatory
	DESCRIPTION
		"This object is used to create and
		delete row in the table and control
		if they are used. The values
		that can be written are:
		  delete(3)...deletes the row
		  create(4)...creates a new row or modifies an exsisting row

		If the row exists, then a SET with
		value of create(4) returns error
		'badValue'. Deleted rows go away
		immediately. The following values
		can be returned on reads:
		  noSuch(0)...no such row
		  other(1)....some other case
		  valid(2)....the row exists and is valid"
	::= { snDhcpGatewayListEntry 3 }


-- DNS MIB Group 

snDnsDomainName OBJECT-TYPE
	SYNTAX	DisplayString (SIZE(0..80))
	ACCESS	read-write
	STATUS	mandatory
	DESCRIPTION
		"DNS Domain Name string."
	::= { snDnsInfo 1 }

snDnsGatewayIpAddrList OBJECT-TYPE
	SYNTAX	OCTET STRING (SIZE(16))
	ACCESS  read-write
	STATUS  mandatory
	DESCRIPTION
		"The DNS Gateway IP address list. This list contains 4 
		IP addresses represented by octet string."
	::= { snDnsInfo 2 }

-- MAC filter table

snMacFilterTable       OBJECT-TYPE
	SYNTAX  SEQUENCE OF SnMacFilterEntry
	ACCESS  not-accessible
	STATUS  mandatory
	DESCRIPTION
		"MAC filter table."
	::= { snMacFilter 1 }

snMacFilterEntry       OBJECT-TYPE
	SYNTAX  SnMacFilterEntry
	ACCESS  not-accessible
	STATUS  mandatory
	DESCRIPTION
		"An entry in the MAC filter table."
	INDEX   { snMacFilterIndex }
	::= { snMacFilterTable 1 }

SnMacFilterEntry ::= SEQUENCE {
	snMacFilterIndex
		INTEGER,
	snMacFilterAction              
		INTEGER,
	snMacFilterSourceMac
		MacAddress,
	snMacFilterSourceMask
		MacAddress,
	snMacFilterDestMac
		MacAddress,
	snMacFilterDestMask
		MacAddress,
	snMacFilterOperator
		INTEGER,
	snMacFilterFrameType
		INTEGER,
	snMacFilterFrameTypeNum
		INTEGER,
	snMacFilterRowStatus
		INTEGER
	}

snMacFilterIndex       OBJECT-TYPE
	SYNTAX  INTEGER
	ACCESS  read-only
	STATUS  mandatory
	DESCRIPTION
		"The table index for a filter entry."
	::= { snMacFilterEntry 1 }

snMacFilterAction      OBJECT-TYPE
	SYNTAX  INTEGER { deny(0), permit(1) } 
	ACCESS  read-write
	STATUS  mandatory
	DESCRIPTION
		"Action to take if the Mac packet match
		with this filter."
	::= { snMacFilterEntry 2 }

snMacFilterSourceMac    OBJECT-TYPE
	SYNTAX  MacAddress
	ACCESS  read-write
	STATUS  mandatory
	DESCRIPTION
		"Source MAC address."
	::= { snMacFilterEntry 3 }

snMacFilterSourceMask  OBJECT-TYPE
	SYNTAX  MacAddress
	ACCESS  read-write
	STATUS  mandatory
	DESCRIPTION
		"Source MAC subnet mask."
	::= { snMacFilterEntry 4 }

snMacFilterDestMac      OBJECT-TYPE
	SYNTAX  MacAddress
	ACCESS  read-write
	STATUS  mandatory
	DESCRIPTION
		"Destination MAC address."
	::= { snMacFilterEntry 5 }

snMacFilterDestMask    OBJECT-TYPE
	SYNTAX  MacAddress
	ACCESS  read-write
	STATUS  mandatory
	DESCRIPTION
		"Destination MAC subnet mask."
	::= { snMacFilterEntry 6 }

snMacFilterOperator    OBJECT-TYPE
	SYNTAX  INTEGER { equal(0), notEqual(1), less(2), greater(3) }
	ACCESS  read-write
	STATUS  mandatory
	DESCRIPTION
		"Type of comparison to perform."
	::= { snMacFilterEntry 7 }

snMacFilterFrameType     OBJECT-TYPE
	SYNTAX  INTEGER{ notUsed(0), ethernet(1), llc(2), snap(3) }
	ACCESS  read-write
	STATUS  mandatory
	DESCRIPTION
		"Frame Type: ethernet-type, LLC and SNAP types"
	::= { snMacFilterEntry 8 }

snMacFilterFrameTypeNum     OBJECT-TYPE
	SYNTAX  INTEGER(0..65535)
	ACCESS  read-write
	STATUS  mandatory
	DESCRIPTION
		"Frame Type Number. 0 means NA"
	::= { snMacFilterEntry 9 }

snMacFilterRowStatus   OBJECT-TYPE
	SYNTAX	 INTEGER {
	    invalid(1),
	    valid(2),
	    delete(3),
	    create(4),
	    modify(5)
	}
	ACCESS	 read-write
	STATUS	 mandatory
	DESCRIPTION
	"This object is used to create and
	 delete row in the table and control
	 if they are used. The values
	 that can be written are:
	 delete(3)...deletes the row
	 create(4)...creates a new row
	 modify(5)...modifies an exsisting row

	 If the row exists, then a SET with
	 value of create(4) returns error
	 'badValue'. Deleted rows go away
	 immediately. The following values
	 can be returned on reads:
	 noSuch(0)...no such row
	 invalid(1)...Setting it to 'invalid' has the effect of
		      rendering it inoperative..
	 valid(2)....the row exists and is valid"
	::= { snMacFilterEntry 10 }

-- MAC Filter Port access table

snMacFilterPortAccessTable           OBJECT-TYPE
	SYNTAX  SEQUENCE OF SnMacFilterPortAccessEntry
	ACCESS  not-accessible
	STATUS  mandatory
	DESCRIPTION
		"MAC Filter port access table."
	::= { snMacFilter 2 }

snMacFilterPortAccessEntry           OBJECT-TYPE
	SYNTAX  SnMacFilterPortAccessEntry
	ACCESS  not-accessible
	STATUS  mandatory
	DESCRIPTION
		"An entry in the MAC Filter Port access table."
	INDEX   { snMacFilterPortAccessPortIndex }
	::= { snMacFilterPortAccessTable 1 }

SnMacFilterPortAccessEntry ::= SEQUENCE {
	snMacFilterPortAccessPortIndex
		INTEGER,
	snMacFilterPortAccessFilters
		OCTET STRING,
	snMacFilterPortAccessRowStatus
		INTEGER
	}

snMacFilterPortAccessPortIndex               OBJECT-TYPE
	SYNTAX  INTEGER (1..3900)
	ACCESS  read-only
	STATUS  mandatory
	DESCRIPTION
		"The port index.
		For FastIron/NetIron products, port index value is from 1 to 42
		For BigIron products, port index is an encoded number:
		The bit 0 to bit 7: port number.
		The bit 8 to bit 11: slot number.
		For virtual router interface, slot number is 15,
		port number is the virtual router port from 1 to 60.
		Therefore, port index value for BigIron is from 257 to 3900."
	::= { snMacFilterPortAccessEntry 1 }

snMacFilterPortAccessFilters                 OBJECT-TYPE
	SYNTAX  OCTET STRING
	ACCESS  read-write
	STATUS  mandatory
	DESCRIPTION
		"1st octet correspond to 1st filter 
		number and so on."
	::= { snMacFilterPortAccessEntry 2 }

snMacFilterPortAccessRowStatus       OBJECT-TYPE
	SYNTAX	 INTEGER {
	    invalid(1),
	    valid(2),
	    delete(3),
	    create(4)
	}
	ACCESS	 read-write
	STATUS	 mandatory
	DESCRIPTION
	"This object is used to create and
	 delete row in the table and control
	 if they are used. The values
	 that can be written are:
	 delete(3)...deletes the row
	 create(4)...creates a new row

	 If the row exists, then a SET with
	 value of create(4) returns error
	 'badValue'. Deleted rows go away
	 immediately. The following values
	 can be returned on reads:
	 noSuch(0)...no such row
	 invalid(1)...Setting it to 'invalid' has the effect of
		      rendering it inoperative..
	 valid(2)....the row exists and is valid"
	::= { snMacFilterPortAccessEntry 3 }

-- NTP general group

snNTPGeneral               OBJECT IDENTIFIER ::= { snNTP 1 }

snNTPPollInterval          OBJECT-TYPE
	SYNTAX  INTEGER (1..65535)
	ACCESS  read-write
	STATUS  mandatory
	DESCRIPTION
		"Interval specifies how often to poll the NTP server.
		Each unit is one second."
    DEFVAL  { 1800 }
	::= { snNTPGeneral 1 }

snNTPTimeZone              OBJECT-TYPE
	SYNTAX  INTEGER {
		alaska(0),
		aleutian(1),
		arizona(2),
		central(3),
		eastIndiana(4),
		eastern(5),
		hawaii(6),
		michigan(7),
		mountain(8),
		pacific(9),
		samoa(10),
		gmtPlus12(11),
		gmtPlus11(12),
		gmtPlus10(13),
		gmtPlus9(14),
		gmtPlus8(15),
		gmtPlus7(16),
		gmtPlus6(17),
		gmtPlus5(18),
		gmtPlus4(19),
		gmtPlus3(20),
		gmtPlus2(21),
		gmtPlus1(22),
		gmt(23),
		gmtMinus1(24),
		gmtMinus2(25),
		gmtMinus3(26),
		gmtMinus4(27),
		gmtMinus5(28),
		gmtMinus6(29),
		gmtMinus7(30),
		gmtMinus8(31),
		gmtMinus9(32),
		gmtMinus10(33),
		gmtMinus11(34),
		gmtMinus12(35) }
	ACCESS  read-write
	STATUS  mandatory
	DESCRIPTION
		"Time zone."
    DEFVAL  { gmt }
	::= { snNTPGeneral 2 }

snNTPSummerTimeEnable      OBJECT-TYPE
	SYNTAX  INTEGER { disabled(0), enabled (1) }
	ACCESS  read-write
	STATUS  mandatory
	DESCRIPTION
		"Enable/Disable daylight saving time. This enables daylight
		saving time for time/date starting 02:00:00 of first Sunday
		in April and ending 02:00:00 of last Sunday in October every
		year."
    DEFVAL  { disabled }
	::= { snNTPGeneral 3 }

snNTPSystemClock           OBJECT-TYPE
	SYNTAX  OCTET STRING (SIZE (7))
	ACCESS  read-write
	STATUS  mandatory
	DESCRIPTION
		"System clock, in the following format:
		octet   0: seconds after the minute [0-60]
		octet   1: minutes after the hour [0-59]
		octet   2: hours since midnight [0-23]
		octet   3: day of the month [1-31]
		octet   4: months since January [0-11]
		octet   5: years since 1900
		octet   6: days since Sunday [0-6]
		Setting this object requires valid value in octets 0 to 5,
		and zero in octet 6. System clock can be disabled by setting
		zero to all octets."
	::= { snNTPGeneral 4 }

snNTPSync                  OBJECT-TYPE
	SYNTAX  INTEGER { other(1), synchronize(2) }
	ACCESS  read-write
	STATUS  mandatory
	DESCRIPTION
		"Initiate time synchronization to the NTP servers.
		For set operation, only 'synchronize(2)' is accepted.
		For get operation, always return 'other(1)'."
	::= { snNTPGeneral 5 }

-- NTP server table

snNTPServerTable           OBJECT-TYPE
	SYNTAX  SEQUENCE OF SnNTPServerEntry
	ACCESS  not-accessible
	STATUS  mandatory
	DESCRIPTION
		"NTP (Network Time Protocol) server table."
	::= { snNTP 2 }

snNTPServerEntry           OBJECT-TYPE
	SYNTAX  SnNTPServerEntry
	ACCESS  not-accessible
	STATUS  mandatory
	DESCRIPTION
		"An entry in the NTP server table."
	INDEX   { snNTPServerIp }
	::= { snNTPServerTable 1 }

SnNTPServerEntry ::= SEQUENCE {
	snNTPServerIp
		IpAddress,
	snNTPServerVersion
		INTEGER,
	snNTPServerRowStatus
		INTEGER
	}

snNTPServerIp              OBJECT-TYPE
	SYNTAX  IpAddress
	ACCESS  read-only
	STATUS  mandatory
	DESCRIPTION
		"NTP server IP address."
	::= { snNTPServerEntry 1 }

snNTPServerVersion         OBJECT-TYPE
	SYNTAX  INTEGER (1..4)
	ACCESS  read-write
	STATUS  mandatory
	DESCRIPTION
		"NTP server version."
    DEFVAL  { 1 }
	::= { snNTPServerEntry 2 }

snNTPServerRowStatus       OBJECT-TYPE
	SYNTAX	INTEGER {
	    other(1),
	    valid(2),
	    delete(3),
	    create(4) }
	ACCESS  read-write
	STATUS  mandatory
	DESCRIPTION
		"To create or delete a NTP server table entry."
	::= { snNTPServerEntry 3 }

-- Radius general group

snRadiusGeneral            OBJECT IDENTIFIER ::= { snRadius 1 }

snRadiusSNMPAccess         OBJECT-TYPE
	SYNTAX  INTEGER { disabled(0), enabled(1) }
	ACCESS  read-only
	STATUS  mandatory
	DESCRIPTION
		"Indicate whether Radius group MIB obejcts can be
		accessed by SNMP manager. If value is disabled,
		all Radius group MIB objects return 'general error'."
    DEFVAL  { disabled }
	::= { snRadiusGeneral 1 }

snRadiusEnableTelnetAuth   OBJECT-TYPE
	SYNTAX  INTEGER { disabled(0), enabled(1) }
	ACCESS  read-write
	STATUS  mandatory
	DESCRIPTION
		"Enable/Disable telnet authentication specified
		by 'snRadiusLoginMethod'."
    DEFVAL  { disabled }
	::= { snRadiusGeneral 2 }

snRadiusRetransmit         OBJECT-TYPE
	SYNTAX  INTEGER (0..5)
	ACCESS  read-write
	STATUS  mandatory
	DESCRIPTION
		"The number of authentication query retransmissions
		to the Radius server."
    DEFVAL  { 3 }
	::= { snRadiusGeneral 3 }

snRadiusTimeOut            OBJECT-TYPE
	SYNTAX  INTEGER (1..60)
	ACCESS  read-write
	STATUS  mandatory
	DESCRIPTION
		"Interval specifies how long to wait for authentication
		reply from the Radius server, each unit is one second."
    DEFVAL  { 3 }
	::= { snRadiusGeneral 4 }

snRadiusDeadTime           OBJECT-TYPE
	SYNTAX  INTEGER (1..5)
	ACCESS  read-write
	STATUS  mandatory
	DESCRIPTION
		"Interval specifies Radius server dead time,
		each unit is one minute."
    DEFVAL  { 3 }
	::= { snRadiusGeneral 5 }

snRadiusKey                OBJECT-TYPE
	SYNTAX  DisplayString (SIZE(0..32))
	ACCESS  read-write
	STATUS  mandatory
	DESCRIPTION
		"Authentication key displayed as encrypted text."
	::= { snRadiusGeneral 6 }

snRadiusLoginMethod        OBJECT-TYPE
	SYNTAX  OCTET STRING (SIZE(0..7))
	ACCESS  read-write
	STATUS  mandatory
	DESCRIPTION
		"A sequence of authentication methods. Each octet represents
		a method to authenticate the user login process. Each octet
		has the following enumeration value:
		  enable(1) - authenticate by command line interface
		              enable password
		  radius(2) - authenticate by requesting radius server
		  local(3) - authenticate by local user account table
		  line(4) - authenticate by telnet password
		  tacplus(5) - authenticate by requesting tacplus server
		  none(6) - do not authenticate
		  tacacs(7) - authenticate by requesting tacacs server
		Setting a zero length octet string invalidates all
		previous authentication methods."
	::= { snRadiusGeneral 7 }

snRadiusEnableMethod       OBJECT-TYPE
	SYNTAX  OCTET STRING (SIZE(0..7))
	ACCESS  read-write
	STATUS  mandatory
	DESCRIPTION
		"A sequence of authentication methods. Each octet represents
		a method to authenticate the user entering priviledge mode
		of the command line interface. Each octet has the following
		enumeration value:
		  enable(1) - authenticate by command line interface
		              enable password
		  radius(2) - authenticate by requesting radius server
		  local(3) - authenticate by local user account table
		  line(4) - authenticate by telnet password
		  tacplus(5) - authenticate by requesting tacplus server
		  none(6) - do not authenticate
		  tacacs(7) - authenticate by requesting tacacs server
		Setting a zero length octet string invalidates all
		previous authentication methods."
	::= { snRadiusGeneral 8 }

snRadiusWebServerMethod    OBJECT-TYPE
	SYNTAX  OCTET STRING (SIZE(0..7))
	ACCESS  read-write
	STATUS  mandatory
	DESCRIPTION
		"A sequence of authentication methods. Each octet represents
		a method to authenticate the user accessing the web-server.
		Each octet has the following enumeration value:
		  enable(1) - authenticate by command line interface
		              enable password
		  radius(2) - authenticate by requesting radius server
		  local(3) - authenticate by local user account table
		  line(4) - authenticate by telnet password
		  tacplus(5) - authenticate by requesting tacplus server
		  none(6) - do not authenticate
		  tacacs(7) - authenticate by requesting tacacs server
		Setting a zero length octet string invalidates all
		previous authentication methods."
	::= { snRadiusGeneral 9 }

snRadiusSNMPServerMethod   OBJECT-TYPE
	SYNTAX  OCTET STRING (SIZE(0..7))
	ACCESS  read-write
	STATUS  mandatory
	DESCRIPTION
		"A sequence of authentication methods. Each octet represents
		a method to authenticate the user accessing the snmp-server.
		Each octet has the following enumeration value:
		  enable(1) - authenticate by command line interface
		              enable password
		  radius(2) - authenticate by requesting radius server
		  local(3) - authenticate by local user account table
		  line(4) - authenticate by telnet password
		  tacplus(5) - authenticate by requesting tacplus server
		  none(6) - do not authenticate
		  tacacs(7) - authenticate by requesting tacacs server
		Setting a zero length octet string invalidates all
		previous authentication methods."
	::= { snRadiusGeneral 10 }

-- Radius server table

snRadiusServerTable        OBJECT-TYPE
	SYNTAX  SEQUENCE OF SnRadiusServerEntry
	ACCESS  not-accessible
	STATUS  mandatory
	DESCRIPTION
		"Radius server table."
	::= { snRadius 2 }

snRadiusServerEntry        OBJECT-TYPE
	SYNTAX  SnRadiusServerEntry
	ACCESS  not-accessible
	STATUS  mandatory
	DESCRIPTION
		"An entry in the Radius server table."
	INDEX   { snRadiusServerIp }
	::= { snRadiusServerTable 1 }

SnRadiusServerEntry ::= SEQUENCE {
	snRadiusServerIp
		IpAddress,
	snRadiusServerAuthPort
		INTEGER,
	snRadiusServerAcctPort
		INTEGER,
	snRadiusServerRowStatus
		INTEGER,
	snRadiusServerRowKey
		DisplayString,
	snRadiusServerUsage
		INTEGER
	}

snRadiusServerIp           OBJECT-TYPE
	SYNTAX  IpAddress
	ACCESS  read-only
	STATUS  mandatory
	DESCRIPTION
		"Radius server IP address."
	::= { snRadiusServerEntry 1 }

snRadiusServerAuthPort     OBJECT-TYPE
	SYNTAX  INTEGER
	ACCESS  read-write
	STATUS  mandatory
	DESCRIPTION
		"Authentication UDP port number."
    DEFVAL  { 1645 }
	::= { snRadiusServerEntry 2 }

snRadiusServerAcctPort     OBJECT-TYPE
	SYNTAX  INTEGER
	ACCESS  read-write
	STATUS  mandatory
	DESCRIPTION
		"Account UDP port number."
    DEFVAL  { 1646 }
	::= { snRadiusServerEntry 3 }

snRadiusServerRowStatus    OBJECT-TYPE
	SYNTAX	INTEGER {
	    other(1),
	    valid(2),
	    delete(3),
	    create(4) }
	ACCESS  read-write
	STATUS  mandatory
	DESCRIPTION
		"To create or delete a Radius server table entry."
	::= { snRadiusServerEntry 4 }

snRadiusServerRowKey       OBJECT-TYPE
	SYNTAX  DisplayString (SIZE(0..32))
	ACCESS  read-write
	STATUS  mandatory
	DESCRIPTION
		"Authentication key displayed as encrypted text."
	::= { snRadiusServerEntry 5 }

snRadiusServerUsage    OBJECT-TYPE
	SYNTAX	INTEGER {
	    default(1),
	    authentication-only(2),
	    authorization-only(3),
	    accounting-only(4) }
	ACCESS  read-write
	STATUS  mandatory
	DESCRIPTION
		"To allow this server to be dedicated for a particular AAA activity."
	::= { snRadiusServerEntry 6 }

--- Tacacs General MIBs

snTacacsGeneral            OBJECT IDENTIFIER ::= { snTacacs 1 }

snTacacsRetransmit         OBJECT-TYPE
	SYNTAX  INTEGER (0..5)
	ACCESS  read-write
	STATUS  mandatory
	DESCRIPTION
		"The number of authentication query retransmissions
		to the Tacacs server."
    DEFVAL  { 3 }
	::= { snTacacsGeneral 1 }

snTacacsTimeOut            OBJECT-TYPE
	SYNTAX  INTEGER (1..15)
	ACCESS  read-write
	STATUS  mandatory
	DESCRIPTION
		"Interval specifies how long to wait for authentication
		reply from the Tacacs server, each unit is one second."
    DEFVAL  { 3 }
	::= { snTacacsGeneral 2 }

snTacacsDeadTime           OBJECT-TYPE
	SYNTAX  INTEGER (1..5)
	ACCESS  read-write
	STATUS  mandatory
	DESCRIPTION
		"Interval specifies Tacacs server dead time,
		each unit is one minute."
    DEFVAL  { 3 }
	::= { snTacacsGeneral 3 }

snTacacsKey                OBJECT-TYPE
	SYNTAX  DisplayString (SIZE(0..32))
	ACCESS  read-write
	STATUS  mandatory
	DESCRIPTION
		"Authentication key displayed as encrypted text."
	::= { snTacacsGeneral 4 }

snTacacsSNMPAccess         OBJECT-TYPE
	SYNTAX  INTEGER { disabled(0), enabled(1) }
	ACCESS  read-only
	STATUS  mandatory
	DESCRIPTION
		"Indicate whether Tacacs group MIB obejcts can be
		accessed by SNMP manager. If value is disabled,
		all Tacacs group MIB objects return 'general error'."
    DEFVAL  { disabled }
	::= { snTacacsGeneral 5 }

-- Tacacs server table

snTacacsServerTable        OBJECT-TYPE
	SYNTAX  SEQUENCE OF SnTacacsServerEntry
	ACCESS  not-accessible
	STATUS  mandatory
	DESCRIPTION
 		"Tacacs server table."
	::= { snTacacs 2 }

snTacacsServerEntry        OBJECT-TYPE
	SYNTAX  SnTacacsServerEntry
	ACCESS  not-accessible
	STATUS  mandatory
	DESCRIPTION
		"An entry in the Tacacs server table."
	INDEX   { snTacacsServerIp }
	::= { snTacacsServerTable 1 }

SnTacacsServerEntry ::= SEQUENCE {
	snTacacsServerIp
		IpAddress,
	snTacacsServerAuthPort
		INTEGER,
	snTacacsServerRowStatus
		INTEGER,
	snTacacsServerRowKey
		DisplayString,
	snTacacsServerUsage
		INTEGER
	}

snTacacsServerIp           OBJECT-TYPE
	SYNTAX  IpAddress
	ACCESS  read-only
	STATUS  mandatory
	DESCRIPTION
		"Tacacs server IP address."
	::= { snTacacsServerEntry 1 }

snTacacsServerAuthPort     OBJECT-TYPE
	SYNTAX  INTEGER
	ACCESS  read-write
	STATUS  mandatory
	DESCRIPTION
		"Authentication UDP port number."
    DEFVAL  { 49 }
	::= { snTacacsServerEntry 2 }

snTacacsServerRowStatus    OBJECT-TYPE
	SYNTAX	INTEGER {
	    other(1),
	    valid(2),
	    delete(3),
	    create(4) }
	ACCESS  read-write
	STATUS  mandatory
	DESCRIPTION
		"To create or delete a Tacacs server table entry."
	::= { snTacacsServerEntry 3 }

snTacacsServerRowKey       OBJECT-TYPE
	SYNTAX  DisplayString (SIZE(0..32))
	ACCESS  read-write
	STATUS  mandatory
	DESCRIPTION
		"Authentication key displayed as encrypted text."
	::= { snTacacsServerEntry 4 }

snTacacsServerUsage    OBJECT-TYPE
	SYNTAX	INTEGER {
	    default(1),
	    authentication-only(2),
	    authorization-only(3),
	    accounting-only(4) }
	ACCESS  read-write
	STATUS  mandatory
	DESCRIPTION
		"To allow this server to be dedicated for a particular AAA activity."
	::= { snTacacsServerEntry 5 }

-- QOS Profile Group

snQosProfileTable OBJECT-TYPE
	SYNTAX  SEQUENCE OF SnQosProfileEntry
	ACCESS  not-accessible
	STATUS  mandatory
	DESCRIPTION
		"A table contains the configuration of qos profile 
		 groups."
	::= { snQos 1 }

snQosProfileEntry OBJECT-TYPE
	SYNTAX  SnQosProfileEntry
	ACCESS  not-accessible
	STATUS  mandatory
	DESCRIPTION
		"An entry of the snQosProfileTable."
	INDEX {snQosProfileIndex}
	::= { snQosProfileTable 1 }

SnQosProfileEntry ::= SEQUENCE {
	snQosProfileIndex
		INTEGER,
	snQosProfileName
		DisplayString,
	snQosProfileRequestedBandwidth
		INTEGER,
	snQosProfileCalculatedBandwidth
		INTEGER
	}

snQosProfileIndex OBJECT-TYPE
	SYNTAX  INTEGER (1..8)
	ACCESS  read-only
	STATUS  mandatory
	DESCRIPTION
		"The table index of QOS Profile." 
	::= { snQosProfileEntry 1 }

snQosProfileName OBJECT-TYPE
	SYNTAX	DisplayString (SIZE(0..32))
	ACCESS	read-write
	STATUS	mandatory
	DESCRIPTION
		"Qos Profile Name string."
	::= { snQosProfileEntry 2 }

snQosProfileRequestedBandwidth OBJECT-TYPE
	SYNTAX  INTEGER (0..100)
	ACCESS  read-write
	STATUS  mandatory
	DESCRIPTION
		"Qos Profile Requested Bandwidth."
	::= { snQosProfileEntry 3 }

snQosProfileCalculatedBandwidth OBJECT-TYPE
	SYNTAX  INTEGER (0..100)
	ACCESS  read-only
	STATUS  mandatory
	DESCRIPTION
		"Qos Profile Calculated Bandwidth."
	::= { snQosProfileEntry 4 }

-- QOS Bind Group

snQosBindTable OBJECT-TYPE
	SYNTAX  SEQUENCE OF SnQosBindEntry
	ACCESS  not-accessible
	STATUS  mandatory
	DESCRIPTION
		"A table contains the configuration of 802.1p to qos profile 
		 binding groups."
	::= { snQos 2 }

snQosBindEntry OBJECT-TYPE
	SYNTAX  SnQosBindEntry
	ACCESS  not-accessible
	STATUS  mandatory
	DESCRIPTION
		"An entry of the snQosBindTable."
	INDEX {snQosBindIndex}
	::= { snQosBindTable 1 }

SnQosBindEntry ::= SEQUENCE {
	snQosBindIndex
		INTEGER,
	snQosBindPriority
		INTEGER,
	snQosBindProfileIndex
		INTEGER
	}

snQosBindIndex OBJECT-TYPE
	SYNTAX  INTEGER (1..8)
	ACCESS  read-only
	STATUS  mandatory
	DESCRIPTION
		"The table index of QOS Bind."
	::= { snQosBindEntry 1 }

snQosBindPriority OBJECT-TYPE
	SYNTAX  INTEGER
	ACCESS  read-only
	STATUS  mandatory
	DESCRIPTION
		 "QOS bind priority."
	::= { snQosBindEntry 2 }

snQosBindProfileIndex OBJECT-TYPE
	SYNTAX  INTEGER (1..8)
	ACCESS  read-write
	STATUS  mandatory
	DESCRIPTION
		"QOS Bind Profile Index. This is pointer to the
		index of snQosProfile Table." 
	::= { snQosBindEntry 3 }

-- Denial of service attack

snDosAttack       OBJECT IDENTIFIER ::= { snQos 3 }
snDosAttackGlobal OBJECT IDENTIFIER ::= { snDosAttack 1 }

snDosAttackICMPDropCount OBJECT-TYPE
	SYNTAX  Counter
	ACCESS  read-only
	STATUS  mandatory
	DESCRIPTION
		"ICMP drop counter."
	::= { snDosAttackGlobal 1 }

snDosAttackICMPBlockCount OBJECT-TYPE
	SYNTAX  Counter
	ACCESS  read-only
	STATUS  mandatory
	DESCRIPTION
		"ICMP block counter."
	::= { snDosAttackGlobal 2 }

snDosAttackSYNDropCount OBJECT-TYPE
	SYNTAX  Counter
	ACCESS  read-only
	STATUS  mandatory
	DESCRIPTION
		"SYN drop counter."
	::= { snDosAttackGlobal 3 }

snDosAttackSYNBlockCount OBJECT-TYPE
	SYNTAX  Counter
	ACCESS  read-only
	STATUS  mandatory
	DESCRIPTION
		"SYN block counter."
	::= { snDosAttackGlobal 4 }

snDosAttackPortTable OBJECT-TYPE
	SYNTAX  SEQUENCE OF SnDosAttackPortEntry
	ACCESS  not-accessible
	STATUS  mandatory
	DESCRIPTION
		"Denial of service attack port table."
	::= { snDosAttack 2 }

snDosAttackPortEntry OBJECT-TYPE
	SYNTAX  SnDosAttackPortEntry
	ACCESS  not-accessible
	STATUS  mandatory
	DESCRIPTION
		"An entry of the denial of service attack port table."
	INDEX {snDosAttackPort}
	::= { snDosAttackPortTable 1 }

SnDosAttackPortEntry ::= SEQUENCE {
	snDosAttackPort
		INTEGER,
	snDosAttackPortICMPDropCount
		Counter,
	snDosAttackPortICMPBlockCount
		Counter,
	snDosAttackPortSYNDropCount
		Counter,
	snDosAttackPortSYNBlockCount
		Counter
	}

snDosAttackPort OBJECT-TYPE
	SYNTAX  INTEGER
	ACCESS  read-only
	STATUS  mandatory
	DESCRIPTION
		"ifIndex value of a port." 
	::= { snDosAttackPortEntry 1 }

snDosAttackPortICMPDropCount OBJECT-TYPE
	SYNTAX  Counter
	ACCESS  read-only
	STATUS  mandatory
	DESCRIPTION
		"ICMP drop counter."
	::= { snDosAttackPortEntry 2 }

snDosAttackPortICMPBlockCount OBJECT-TYPE
	SYNTAX  Counter
	ACCESS  read-only
	STATUS  mandatory
	DESCRIPTION
		"ICMP block counter."
	::= { snDosAttackPortEntry 3 }

snDosAttackPortSYNDropCount OBJECT-TYPE
	SYNTAX  Counter
	ACCESS  read-only
	STATUS  mandatory
	DESCRIPTION
		"SYN drop counter."
	::= { snDosAttackPortEntry 4 }

snDosAttackPortSYNBlockCount OBJECT-TYPE
	SYNTAX  Counter
	ACCESS  read-only
	STATUS  mandatory
	DESCRIPTION
		"SYN block counter."
	::= { snDosAttackPortEntry 5 }

-- AAA Mib

snAuthentication			OBJECT IDENTIFIER ::= { snAAA 1 }
snAuthorization				OBJECT IDENTIFIER ::= { snAAA 2 }
snAccounting				OBJECT IDENTIFIER ::= { snAAA 3 }

snAuthorizationCommandMethods        OBJECT-TYPE
	SYNTAX  OCTET STRING (SIZE(0..3))
	ACCESS  read-write
	STATUS  mandatory
	DESCRIPTION
		"A sequence of authorization methods. Each octet represents
		a method to authorize the user command. Each octet
		has the following value:
		  radius(2) - authorize by requesting radius server
		  tacplus(5) - authorize by requesting tacplus server
		  none(6) - skip authorization
		Setting a zero length octet string invalidates all
		previous authorization methods."
	::= { snAuthorization 1 }

snAuthorizationCommandLevel OBJECT-TYPE
	SYNTAX  INTEGER {
                 level0(0),
                 level4(4),
				 level5(5)
                    }
	ACCESS  read-write
	STATUS  mandatory
	DESCRIPTION
		"Commands, which are equal to and less than the specified
		command level here needs to be authorized. Possible enumeration
		values:
		0 - Privilege level 0
		4 - Privilege level 4
		5 - Privilege level 5." 
	::= { snAuthorization 2 }

snAuthorizationExec        OBJECT-TYPE
	SYNTAX  OCTET STRING (SIZE(0..3))
	ACCESS  read-write
	STATUS  mandatory
	DESCRIPTION
		"A sequence of exec authorization methods. Each octet represents
		a method for telnet or SSH login authorization. Each octet
		has the following enumeration value:
		  radius(2) - send exec authorization request to radius server
		  tacplus(5) - send exec authorization request to tacplus server
		  none(6) - no exec authorization
		Setting a zero length octet string invalidates all
		authorization methods."
	::= { snAuthorization 3 }


snAccountingCommandMethods        OBJECT-TYPE
	SYNTAX  OCTET STRING (SIZE(0..3))
	ACCESS  read-write
	STATUS  mandatory
	DESCRIPTION
		"A sequence of accounting methods. Each octet represents
		a method to account for the user command. Each octet
		has the following enumeration value:
		  radius(2) - send accounting info to radius server
		  tacplus(5) - send accounting info to tacplus server
		  none(6) - skip accounting
		Setting a zero length octet string invalidates all
		previous accounting methods."
	::= { snAccounting 1 }

snAccountingCommandLevel OBJECT-TYPE
	SYNTAX  INTEGER {
                 level0(0),
                 level4(4),
				 level5(5)
                    }
	ACCESS  read-write
	STATUS  mandatory
	DESCRIPTION
		"Commands, which are equal to and less than the specified
		command level here will be accounted. Possible enumeration
		values:
		level0 - Privilege level 0
		level4 - Privilege level 4
		level5 - Privilege level 5." 
	::= { snAccounting 2 }

snAccountingExec        OBJECT-TYPE
	SYNTAX  OCTET STRING (SIZE(0..3))
	ACCESS  read-write
	STATUS  mandatory
	DESCRIPTION
		"A sequence of accounting methods. Each octet represents
		a method for telnet or SSH login accounting. Each octet
		has the following enumeration value:
		  radius(2) - send accounting info to radius server
		  tacplus(5) - send accounting info to tacplus server
		  none(6) - skip accounting
		Setting a zero length octet string invalidates all
		previous accounting methods."
	::= { snAccounting 3 }

snAccountingSystem        OBJECT-TYPE
	SYNTAX  OCTET STRING (SIZE(0..3))
	ACCESS  read-write
	STATUS  mandatory
	DESCRIPTION
		"A sequence of accounting methods. Each octet represents
		a method to account for the system related events. Each octet
		has the following enumeration value:
		  radius(2) - send accounting info to radius server
		  tacplus(5) - send accounting info to tacplus server
		  none(6) - skip accounting
		Setting a zero length octet string invalidates all
		previous accounting methods."
	::= { snAccounting 4 }

-- NetFlow Mib

snNetFlowGlb	OBJECT IDENTIFIER ::= { snNetFlow 1 }

snNetFlowGblEnable OBJECT-TYPE
	SYNTAX	INTEGER { disabled(0), enabled(1) }
	ACCESS	read-write
	STATUS	mandatory
	DESCRIPTION
		"Enable/disable NetFlow export operation."
    DEFVAL { disabled }
	::= { snNetFlowGlb 1 }

snNetFlowGblVersion OBJECT-TYPE
	SYNTAX	INTEGER { versionNotSet (0), version1 (1), version5 (5) }
	ACCESS	read-write
	STATUS	mandatory
	DESCRIPTION
		"NetFlow export version."
    DEFVAL { version5 }
	::= { snNetFlowGlb 2 }

snNetFlowGblProtocolDisable OBJECT-TYPE
	SYNTAX	INTEGER
	ACCESS	read-write
	STATUS	mandatory
	DESCRIPTION
		"bit 0 - other, disable all protocols export except UDP and TCP
		 bit 1 - tcp, disable TCP protocol export
		 bit 2 - udp, disable UDP protocol export"
    DEFVAL { 0 }
	::= { snNetFlowGlb 3 }

snNetFlowGblActiveTimeout OBJECT-TYPE
	SYNTAX	INTEGER
	ACCESS	read-write
	STATUS	mandatory
	DESCRIPTION
		"Maximum time an active flow can be in the NetFlow cache (minutes: 1..60)"
    DEFVAL { 60 }
	::= { snNetFlowGlb 4 }

snNetFlowGblInactiveTimeout OBJECT-TYPE
	SYNTAX	INTEGER
	ACCESS	read-write
	STATUS	mandatory
	DESCRIPTION
		"Maximum time an inactive flow can be in the NetFlow cache (seconds: 10..600)"
    DEFVAL { 60 }
	::= { snNetFlowGlb 5 }


-- NetFlow Collector Table


snNetFlowCollectorTable OBJECT-TYPE
	SYNTAX	SEQUENCE OF SnNetFlowCollectorEntry
	ACCESS	not-accessible
	STATUS	mandatory
	DESCRIPTION
		"A table of each NetFlow collector information."
	::= { snNetFlow 2 }

snNetFlowCollectorEntry OBJECT-TYPE
	SYNTAX	SnNetFlowCollectorEntry
	ACCESS	not-accessible
	STATUS	mandatory
	DESCRIPTION
		"A row in the NetFlow collector table."
	INDEX	{ snNetFlowCollectorIndex }
	::= { snNetFlowCollectorTable 1 }

SnNetFlowCollectorEntry ::= SEQUENCE {
	snNetFlowCollectorIndex
		INTEGER,
	snNetFlowCollectorIp
		IpAddress,
	snNetFlowCollectorUdpPort
		INTEGER,
	snNetFlowCollectorSourceInterface
		INTEGER,
	snNetFlowCollectorRowStatus
		INTEGER
	}

snNetFlowCollectorIndex OBJECT-TYPE
	SYNTAX	INTEGER (1..10)
	ACCESS	read-only
	STATUS	mandatory
	DESCRIPTION
		"The index to the NetFlow collector table."
	::= { snNetFlowCollectorEntry 1 }

snNetFlowCollectorIp OBJECT-TYPE
	SYNTAX	IpAddress
	ACCESS	read-write
	STATUS	mandatory
	DESCRIPTION
		"The NetFlow collector ip address."
	::= { snNetFlowCollectorEntry 2 }

snNetFlowCollectorUdpPort OBJECT-TYPE
	SYNTAX	INTEGER
	ACCESS	read-write
	STATUS	mandatory
	DESCRIPTION
		"The NetFlow collector UDP port number."
	::= { snNetFlowCollectorEntry 3 }

snNetFlowCollectorSourceInterface OBJECT-TYPE
	SYNTAX	INTEGER
	ACCESS	read-write
	STATUS	mandatory
	DESCRIPTION
		"The ifIndex value to specify source port to
		 export NetFlow packet. Value 0 to indicate
		 default outgoing port."
	::= { snNetFlowCollectorEntry 4 }


snNetFlowCollectorRowStatus OBJECT-TYPE
	SYNTAX	INTEGER	{
		other(1),
		valid(2),
		delete(3),
		create(4) }
	ACCESS	read-write
	STATUS	mandatory
	DESCRIPTION
		"To create or delete a NetFlow collector table entry."
	::= { snNetFlowCollectorEntry 5 }



-- NetFlow Aggregation Table


snNetFlowAggregationTable OBJECT-TYPE
	SYNTAX	SEQUENCE OF SnNetFlowAggregationEntry
	ACCESS	not-accessible
	STATUS	mandatory
	DESCRIPTION
		"A table of each NetFlow aggregation scheme information."
	::= { snNetFlow 3 }

snNetFlowAggregationEntry OBJECT-TYPE
	SYNTAX	SnNetFlowAggregationEntry
	ACCESS	not-accessible
	STATUS	mandatory
	DESCRIPTION
		"A row in the NetFlow Aggregation table."
	INDEX	{ snNetFlowAggregationIndex }
	::= { snNetFlowAggregationTable 1 }

SnNetFlowAggregationEntry ::= SEQUENCE {
	snNetFlowAggregationIndex
		INTEGER,
	snNetFlowAggregationIp
		IpAddress,
	snNetFlowAggregationUdpPort
		INTEGER,
	snNetFlowAggregationSourceInterface
		INTEGER,
	snNetFlowAggregationNumberOfCacheEntries
		INTEGER,
	snNetFlowAggregationActiveTimeout
		INTEGER,
	snNetFlowAggregationInactiveTimeout
		INTEGER,
    snNetFlowAggregationEnable
		INTEGER,
    snNetFlowAggregationRowStatus
		INTEGER
	}

snNetFlowAggregationIndex OBJECT-TYPE
	SYNTAX	INTEGER { as (1), protocolPort (2), destPrefix (3),
	                 sourcePrefix (4), prefix (5) }
	ACCESS	read-only
	STATUS	mandatory
	DESCRIPTION
		"The Aggregation scheme ID"      
	::= { snNetFlowAggregationEntry 1 }

snNetFlowAggregationIp OBJECT-TYPE
	SYNTAX	IpAddress
	ACCESS	read-write
	STATUS	mandatory
	DESCRIPTION
		"The NetFlow aggregation collector ip address."
	::= { snNetFlowAggregationEntry 2 }

snNetFlowAggregationUdpPort OBJECT-TYPE
	SYNTAX	INTEGER
	ACCESS	read-write
	STATUS	mandatory
	DESCRIPTION
		"The NetFlow aggregation collector UDP port number."
	::= { snNetFlowAggregationEntry 3 }

snNetFlowAggregationSourceInterface OBJECT-TYPE
	SYNTAX	INTEGER
	ACCESS	read-write
	STATUS	mandatory
	DESCRIPTION
		"The ifIndex value to specify source port to
		 export NetFlow aggregation packet.
		 Value 0 to indicate default outgoing port."
	::= { snNetFlowAggregationEntry 4 }

snNetFlowAggregationNumberOfCacheEntries OBJECT-TYPE
	SYNTAX	INTEGER
	ACCESS	read-write
	STATUS	mandatory
	DESCRIPTION
		"Number of cache entries for aggregation scheme"
	::= { snNetFlowAggregationEntry 5 }

snNetFlowAggregationActiveTimeout OBJECT-TYPE
	SYNTAX	INTEGER
	ACCESS	read-write
	STATUS	mandatory
	DESCRIPTION
		"Maximum time an active flow can be in
		 the aggregation cache"
	::= { snNetFlowAggregationEntry 6 }

snNetFlowAggregationInactiveTimeout OBJECT-TYPE
	SYNTAX	INTEGER
	ACCESS	read-write
	STATUS	mandatory
	DESCRIPTION
		"Maximum time an inactive flow can be in
		 the aggregation cache"
	::= { snNetFlowAggregationEntry 7 }

snNetFlowAggregationEnable OBJECT-TYPE
	SYNTAX	INTEGER { disabled(0), enabled(1) }
	ACCESS	read-write
	STATUS	mandatory
	DESCRIPTION
		"Enable/disable NetFlow aggregation
		 for this aggregation scheme."
    DEFVAL { disabled }
	::= {  snNetFlowAggregationEntry 8 }

snNetFlowAggregationRowStatus OBJECT-TYPE
	SYNTAX	INTEGER	{
		other(1),
		valid(2),
		delete(3),
		create(4) }
	ACCESS	read-write
	STATUS	mandatory
	DESCRIPTION
		"To create or delete a NetFlow collector table entry."
	::= { snNetFlowAggregationEntry 9 }


-- NetFlow Interface Table

-- Table containing information about the switching
-- type in every interface.

snNetFlowIfTable OBJECT-TYPE
	SYNTAX	SEQUENCE OF SnNetFlowIfEntry
	ACCESS	not-accessible
	STATUS	mandatory
	DESCRIPTION
		"A list of interface entries.  The number of entries
         is given by the value of ifNumber."
	::= { snNetFlow 4 }

snNetFlowIfEntry OBJECT-TYPE
	SYNTAX	SnNetFlowIfEntry
	ACCESS	not-accessible
	STATUS	mandatory
	DESCRIPTION
		"Entry containing the type of switching performed
		 on that interface."
	INDEX	{ snNetFlowIfIndex }
	::= { snNetFlowIfTable 1 }

SnNetFlowIfEntry ::= SEQUENCE {
	snNetFlowIfIndex
		INTEGER,
	snNetFlowIfFlowSwitching
		INTEGER
	}

 snNetFlowIfIndex OBJECT-TYPE
       SYNTAX      INTEGER (1..65536)
       ACCESS      read-only
       STATUS      mandatory
       DESCRIPTION
           "A unique value, greater than zero, for each
            interface.  It is recommended that values are assigned
            contiguously starting from 1.  The value for each
            interface sub-layer must remain constant at least from
            one re-initialization of the entity's network
            management system to the next re-initialization."
       ::= { snNetFlowIfEntry 1 }

snNetFlowIfFlowSwitching OBJECT-TYPE
       SYNTAX      INTEGER { disabled (0), enabled (1) }
       ACCESS      read-write
       STATUS      mandatory
       DESCRIPTION
           "To enable/disable flow switching in a particular
		    interface:
			disable (0) - no flow switching
			enable  (1) - flow switching"
       ::= { snNetFlowIfEntry 2 }

-- sFlow Collector Table.

snSFlowGlb	OBJECT IDENTIFIER ::= { snSFlow 1 }

snSflowCollectorTable     OBJECT-TYPE
	SYNTAX	SEQUENCE OF SnSflowCollectorEntry
	ACCESS	not-accessible
	STATUS	mandatory
	DESCRIPTION
		"Table of all but first sFlow collectors. The first collector can be configured
		using sFlowTable in RFC 3176. The RFC cannot be used to configure more
		than one sFlow collectors. This table has been created to fill this gap."
	::= { snSFlow 2 }

snSflowCollectorEntry	OBJECT-TYPE
	SYNTAX	SnSflowCollectorEntry
	ACCESS	not-accessible
	STATUS	mandatory
	DESCRIPTION
		"A row in the sFlow collector table."
	INDEX	{ snSflowCollectorIndex }
	::= { snSflowCollectorTable 1 }

SnSflowCollectorEntry ::= SEQUENCE {
	snSflowCollectorIndex
		INTEGER,
	snSflowCollectorIP
		IpAddress,
	snSflowCollectorUDPPort
		INTEGER,
	snSflowCollectorRowStatus
		INTEGER
	}

snSflowCollectorIndex  OBJECT-TYPE
	SYNTAX	INTEGER
	ACCESS	read-only
	STATUS	mandatory
	DESCRIPTION
		"The index to the sFlow collector table."
	::= { snSflowCollectorEntry 1 }

snSflowCollectorIP OBJECT-TYPE
	SYNTAX	IpAddress
	ACCESS	read-write
	STATUS	mandatory
	DESCRIPTION
		"The sFlow collector ip address."
	::= { snSflowCollectorEntry 2 }

snSflowCollectorUDPPort OBJECT-TYPE
	SYNTAX	INTEGER
	ACCESS	read-write
	STATUS	mandatory
	DESCRIPTION
		"The sFlow collector UDP port number."
	::= { snSflowCollectorEntry 3 }

snSflowCollectorRowStatus OBJECT-TYPE
	SYNTAX	INTEGER	{
		noSuch(0),
		other(1),
		valid(2),
		delete(3),
		create(4),
		modify(5)
		}
	ACCESS	read-write
	STATUS	mandatory
	DESCRIPTION
		"To create, update or delete a SFlow collector table entry.
		If the row exists, then a SET with
		value of create(4) returns error
		'badValue'. Deleted rows go away
		immediately. The following values
		can be returned on reads:
		  noSuch(0)...no such row
		  other(1)....some other case
		  valid(2)....the row exists and is valid"
	::= { snSflowCollectorEntry 4 }


snFdpMIBObjects OBJECT IDENTIFIER ::= { snFDP 1 }

snFdpInterface   OBJECT IDENTIFIER ::= { snFdpMIBObjects 1 }
snFdpCache       OBJECT IDENTIFIER ::= { snFdpMIBObjects 2 }
snFdpGlobal      OBJECT IDENTIFIER ::= { snFdpMIBObjects 3 }
snFdpCachedAddr  OBJECT IDENTIFIER ::= { snFdpMIBObjects 4 }

--
-- FDP Interface Group
--
snFdpInterfaceTable OBJECT-TYPE
    SYNTAX     SEQUENCE OF FdpInterfaceEntry
    ACCESS     not-accessible
    STATUS     mandatory
    DESCRIPTION
            "Status of FDP on the device's interfaces."
    ::= { snFdpInterface 1 }

snFdpInterfaceEntry OBJECT-TYPE
    SYNTAX     FdpInterfaceEntry
    ACCESS     not-accessible
    STATUS     mandatory
    DESCRIPTION
            "An entry in the snFdpInterfaceTable,
            having the status of FDP on an interface."
    INDEX      { snFdpInterfaceIfIndex }
    ::= { snFdpInterfaceTable 1 }

FdpInterfaceEntry ::= SEQUENCE {
    snFdpInterfaceIfIndex           INTEGER,
    snFdpInterfaceFdpEnable            INTEGER,
    snFdpInterfaceCdpEnable            INTEGER
}

snFdpInterfaceIfIndex OBJECT-TYPE
    SYNTAX     INTEGER
    ACCESS     not-accessible
    STATUS     mandatory
    DESCRIPTION
            "ifIndex value of the local interface."
    ::= { snFdpInterfaceEntry 1 }

snFdpInterfaceFdpEnable OBJECT-TYPE
    SYNTAX     INTEGER { false(0), true(1) }
    ACCESS     read-write
    STATUS     mandatory
    DESCRIPTION
            "The flag, whether the Foundry Discovery Protocol
            is currently running on this interface.  It has no
            effect when FDP is disabled (snFdpGlobalRun = FALSE)."
	DEFVAL { true }
    ::= { snFdpInterfaceEntry 2 }

snFdpInterfaceCdpEnable OBJECT-TYPE
    SYNTAX     INTEGER { false(0), true(1) }
    ACCESS     read-write
    STATUS     mandatory
    DESCRIPTION
            "The flag, whether the Cisco Discovery Protocol
            is currently running on this interface.  It has no
            effect when CDP is disabled (snCdpGlobalRun = FALSE)."
	DEFVAL { true }
    ::= { snFdpInterfaceEntry 3 }

--
-- FDP Cache Table
--

snFdpCacheTable OBJECT-TYPE
    SYNTAX     SEQUENCE OF FdpCacheEntry
    ACCESS     not-accessible
    STATUS     mandatory
    DESCRIPTION
            "The table for the cached information obtained
             via receiving FDP/CDP messages."
    ::= { snFdpCache 1 }

snFdpCacheEntry OBJECT-TYPE
    SYNTAX     FdpCacheEntry
    ACCESS     not-accessible
    STATUS     mandatory
    DESCRIPTION
            "An entry in the snFdpCacheTable, having the information 
            received via FDP/CDP on one interface from one device.  
            Entries appear when a FDP/CDP advertisement is received
            from a neighbor device.
            Entries disappear when FDP/CDP is disabled on the interface, or globally."
    INDEX      { snFdpCacheIfIndex, snFdpCacheDeviceIndex }
    ::= { snFdpCacheTable 1 }

FdpCacheEntry ::= SEQUENCE {
    snFdpCacheIfIndex					INTEGER,
    snFdpCacheDeviceIndex				INTEGER,
    snFdpCacheDeviceId					DisplayString,
    snFdpCacheAddressType				INTEGER,
    snFdpCacheAddress					OCTET STRING,
    snFdpCacheVersion					DisplayString,
    snFdpCacheDevicePort				DisplayString,
    snFdpCachePlatform					DisplayString,
    snFdpCacheCapabilities				DisplayString, 
    snFdpCacheVendorId					INTEGER, 
	snFdpCacheIsAggregateVlan		INTEGER,
	snFdpCacheTagType				INTEGER,
	snFdpCachePortVlanMask		OCTET STRING,
	snFdpCachePortTagMode         INTEGER,
	snFdpCacheDefaultTrafficeVlanIdForDualMode  INTEGER
}

snFdpCacheIfIndex OBJECT-TYPE
    SYNTAX     INTEGER
    ACCESS     not-accessible
    STATUS     mandatory
    DESCRIPTION
            "ifIndex value of the local interface."
    ::= { snFdpCacheEntry 1 }

snFdpCacheDeviceIndex OBJECT-TYPE
    SYNTAX     INTEGER
    ACCESS     not-accessible
    STATUS     mandatory
    DESCRIPTION
            "Identification of a device, which sent FDP/CDP messages"
    ::= { snFdpCacheEntry 2 }

snFdpCacheDeviceId OBJECT-TYPE
    SYNTAX     DisplayString
    ACCESS     read-only
    STATUS     mandatory
    DESCRIPTION
            "The Device-ID string as reported in the most recent FDP/CDP
            message.  The zero-length string indicates no Device-ID
            field (TLV) was reported in the most recent FDP/CDP
            message."
    ::= { snFdpCacheEntry 3 }

snFdpCacheAddressType OBJECT-TYPE
    SYNTAX     INTEGER { ip(1), ipx(2), appletalk(3) }
    ACCESS     read-only
    STATUS     mandatory
    DESCRIPTION
            "An indication of the type of address contained in the
            corresponding instance of snFdpCacheAddress."
    ::= { snFdpCacheEntry 4 }

snFdpCacheAddress OBJECT-TYPE
    SYNTAX     OCTET STRING
    ACCESS     read-only
    STATUS     mandatory
    DESCRIPTION
            "The (first) network-layer address of the device
            as reported in the most recent FDP/CDP message
			in the following format:
              IP address:  4 octets, ip(1)
              IPX address: 10 octets, ipx(2)
                     First 4-octet as the network number
                     Second 6-octet as the host number
              Appletalk address: 3 octets, appletalk(3)
                     First 2-octet as the network number
                     Second 1-octet as the host number"
    ::= { snFdpCacheEntry 5 }

snFdpCacheVersion OBJECT-TYPE
    SYNTAX     DisplayString
    ACCESS     read-only
    STATUS     mandatory
    DESCRIPTION
            "Version string as reported in the most recent FDP/CDP message. "
    ::= { snFdpCacheEntry 6 }


snFdpCacheDevicePort OBJECT-TYPE
    SYNTAX     DisplayString
    ACCESS     read-only
    STATUS     mandatory
    DESCRIPTION
            "The Port-ID string as reported in the most recent FDP/CDP
            message.  This will typically be the value of the ifName
            object (e.g., Ethernet0).  The zero-length string
            indicates no Port-ID field (TLV) was reported in the
            most recent FDP/CDP message."
    ::= { snFdpCacheEntry 7 }

snFdpCachePlatform OBJECT-TYPE
    SYNTAX     DisplayString
    ACCESS     read-only
    STATUS     mandatory
    DESCRIPTION
            "The Device's Hardware Platform as reported in the most
            recent FDP/CDP message.  The zero-length string indicates
            that no Platform field (TLV) was reported in the most
            recent FDP/CDP message."
    ::= { snFdpCacheEntry 8 }

snFdpCacheCapabilities OBJECT-TYPE
    SYNTAX     DisplayString
    ACCESS     read-only
    STATUS     mandatory
    DESCRIPTION
            "The Device's Functional Capabilities as reported in the
            most recent FDP/CDP message. "
    ::= { snFdpCacheEntry 9 }

snFdpCacheVendorId OBJECT-TYPE
    SYNTAX     INTEGER { fdp(1), cdp(2) }
    ACCESS     read-only
    STATUS     mandatory
    DESCRIPTION
            "Indicates the entry received by either FDP or CDP."
    ::= { snFdpCacheEntry 10 }

snFdpCacheIsAggregateVlan OBJECT-TYPE
    SYNTAX     INTEGER { false(0), true(1) }
    ACCESS     read-only
    STATUS     mandatory
    DESCRIPTION
            "Neighbor device is in aggregated-vlan."
    ::= { snFdpCacheEntry 11 }

snFdpCacheTagType OBJECT-TYPE
    SYNTAX     INTEGER
    ACCESS     read-only
    STATUS     mandatory
    DESCRIPTION
            "Neighbor device tag-type."
    ::= { snFdpCacheEntry 12 }

snFdpCachePortVlanMask OBJECT-TYPE
    SYNTAX     OCTET STRING
    ACCESS     read-only
    STATUS     mandatory
    DESCRIPTION
            "Neighbor device port VLAN masks in 512-byte octet string."
    ::= { snFdpCacheEntry 13 }

snFdpCachePortTagMode OBJECT-TYPE
    SYNTAX     INTEGER { untagged(1), tagged(2), dual(3) }
    ACCESS     read-only
    STATUS     mandatory
    DESCRIPTION
            "Neighbor device port tag mode"
    ::= { snFdpCacheEntry 14 }

snFdpCacheDefaultTrafficeVlanIdForDualMode OBJECT-TYPE
    SYNTAX     INTEGER
    ACCESS     read-only
    STATUS     mandatory
    DESCRIPTION
            "Default traffic vlan id for neighbor device dual-mode port"
    ::= { snFdpCacheEntry 15 }

--
-- FDP Global Group
--   

snFdpGlobalRun OBJECT-TYPE
    SYNTAX     INTEGER { false(0), true(1) }
    ACCESS     read-write
    STATUS     mandatory
    DESCRIPTION
            "The flag, whether the Foundry Discovery Protocol
            is currently running.  FDP entries in snFdpCacheTable are
            deleted when FDP is disabled."
    DEFVAL     { false }
    ::= { snFdpGlobal 1 }

snFdpGlobalMessageInterval OBJECT-TYPE
    SYNTAX     INTEGER (5..900)
    ACCESS     read-write
    STATUS     mandatory
    DESCRIPTION
            "The interval at which FDP messages are to be generated.
            The default value is 60 seconds."
    DEFVAL     { 60 }
    ::= { snFdpGlobal 2 }

snFdpGlobalHoldTime OBJECT-TYPE
    SYNTAX     INTEGER (10..255)
    ACCESS     read-write
    STATUS     mandatory
    DESCRIPTION
            "The time for the receiving device holds FDP message.
            The default value is 180 seconds."
    DEFVAL     { 180 }
    ::= { snFdpGlobal 3 }

snFdpGlobalCdpRun OBJECT-TYPE
    SYNTAX     INTEGER { false(0), true(1) }
    ACCESS     read-write
    STATUS     mandatory
    DESCRIPTION
            "An indication of whether the Cisco Discovery Protocol
            is currently running.  CDP entries in snFdpCacheTable are
            deleted when CDP is disabled."
    DEFVAL     { false }
    ::= { snFdpGlobal 4 }

--
-- FDP Cached Address Entry Table
--
snFdpCachedAddressTable OBJECT-TYPE
    SYNTAX     SEQUENCE OF FdpCachedAddressEntry
    ACCESS     not-accessible
    STATUS     mandatory
    DESCRIPTION
            "Cached address table from receiving FDP/CDP messages."
    ::= { snFdpCachedAddr 1 }

snFdpCachedAddressEntry OBJECT-TYPE
    SYNTAX     FdpCachedAddressEntry
    ACCESS     not-accessible
    STATUS     mandatory
    DESCRIPTION
            "An entry (conceptual row) in the snFdpCacheAddressTable,
            containing one cached address from FDP/CDP messages."
    INDEX      { snFdpCachedAddrIfIndex, snFdpCachedAddrDeviceIndex, snFdpCachedAddrDeviceAddrEntryIndex }
    ::= { snFdpCachedAddressTable 1 }

FdpCachedAddressEntry ::= SEQUENCE {
    snFdpCachedAddrIfIndex               INTEGER,
    snFdpCachedAddrDeviceIndex           INTEGER,
    snFdpCachedAddrDeviceAddrEntryIndex  INTEGER,
    snFdpCachedAddrType				     INTEGER,
    snFdpCachedAddrValue				 OCTET STRING
}

snFdpCachedAddrIfIndex OBJECT-TYPE
    SYNTAX     INTEGER
    ACCESS     not-accessible
    STATUS     mandatory
    DESCRIPTION
            "The ifIndex value of the local interface."
    ::= { snFdpCachedAddressEntry 1 }

snFdpCachedAddrDeviceIndex OBJECT-TYPE
    SYNTAX     INTEGER
    ACCESS     not-accessible
    STATUS     mandatory
    DESCRIPTION
            "A unique vlaue for each device from which FDP/CDP messages
			are being received."
    ::= { snFdpCachedAddressEntry 2 }

snFdpCachedAddrDeviceAddrEntryIndex OBJECT-TYPE
    SYNTAX     INTEGER
    ACCESS     not-accessible
    STATUS     mandatory
    DESCRIPTION
            "A unique vlaue for address entry in device from which FDP/CDP messages
			are being received."
    ::= { snFdpCachedAddressEntry 3 }

snFdpCachedAddrType OBJECT-TYPE
    SYNTAX     INTEGER { ip(1), ipx(2), appletalk(3) }
    ACCESS     read-only
    STATUS     mandatory
    DESCRIPTION
			"An indication of the type of address contained in the
            corresponding instance of snFdpCacheAddrValue."
	::= { snFdpCachedAddressEntry 4 }

snFdpCachedAddrValue OBJECT-TYPE
    SYNTAX     OCTET STRING
    ACCESS     read-only
    STATUS     mandatory
    DESCRIPTION
            "The network-layer address of the device
            SNMP-agent as reported in the most recent FDP/CDP message
			in the following format:
              IP address:  4 octets, ip(1)
              IPX address: 10 octets, ipx(2)
                     First 4-octet as the network number
                     Second 6-octet as the host number
              Appletalk address: 3 octets, appletalk(3)
                     First 2-octet as the network number
                     Second 1-octet as the host number"
    ::= { snFdpCachedAddressEntry 5 }


snMacSecurity   OBJECT IDENTIFIER ::= { snMac 1 }
snPortMacSecurity   OBJECT IDENTIFIER ::= { snMacSecurity 1 }

--
-- Port MAC Security Table
--

snPortMacSecurityTable OBJECT-TYPE
    SYNTAX     SEQUENCE OF PortMacSecurityEntry
    ACCESS     not-accessible
    STATUS     mandatory
    DESCRIPTION
            "Status of port MAC security on the device's interfaces."
    ::= { snPortMacSecurity 1 }

snPortMacSecurityEntry OBJECT-TYPE
    SYNTAX     PortMacSecurityEntry
    ACCESS     not-accessible
    STATUS     mandatory
    DESCRIPTION
            "An entry in the snPortMacSecurityTable"
    INDEX      { snPortMacSecurityIfIndex,
                     snPortMacSecurityResource,
                     snPortMacSecurityQueryIndex
                  }
    ::= { snPortMacSecurityTable 1 }

PortMacSecurityEntry ::= SEQUENCE {
    snPortMacSecurityIfIndex                    Unsigned32,
    snPortMacSecurityResource                 INTEGER,
    snPortMacSecurityQueryIndex              Unsigned32,
    snPortMacSecurityMAC                       MacAddress,
    snPortMacSecurityAgeLeft                  Unsigned32,
    snPortMacSecurityShutdownStatus       INTEGER,
    snPortMacSecurityShutdownTimeLeft   Unsigned32,
    snPortMacSecurityVlanId                    Unsigned32
}

snPortMacSecurityIfIndex     OBJECT-TYPE
    SYNTAX     Unsigned32
    ACCESS     read-only
    STATUS     mandatory
    DESCRIPTION
            "ifIndex value of the local Ethernet interface on 
            which MAC security is configured."
    ::= {snPortMacSecurityEntry 1}

snPortMacSecurityResource OBJECT-TYPE
    SYNTAX     INTEGER { local(1), shared(2) }
    ACCESS     read-only
    STATUS     mandatory
    DESCRIPTION
            "The MAC address was secured using local or shared resources."
    ::= {snPortMacSecurityEntry 2}

snPortMacSecurityQueryIndex     OBJECT-TYPE
    SYNTAX     Unsigned32
    ACCESS     read-only
    STATUS     mandatory
    DESCRIPTION
            "Entry index within the given resource of local Ethernet interface on 
            which MAC security is configured."
    ::= {snPortMacSecurityEntry 3}

snPortMacSecurityMAC OBJECT-TYPE
    SYNTAX     MacAddress
    ACCESS     read-only
    STATUS     mandatory
    DESCRIPTION
            "The secure MAC address for this interface."
    ::= {snPortMacSecurityEntry 4}

snPortMacSecurityAgeLeft OBJECT-TYPE
    SYNTAX     Unsigned32
    ACCESS     read-only
    STATUS     mandatory
    DESCRIPTION
            "The number of minutes the MAC address will remain secure
            before being aged out. 0 means no aging."
    ::= {snPortMacSecurityEntry 5}

snPortMacSecurityShutdownStatus OBJECT-TYPE
    SYNTAX     INTEGER { up(1), down(2) }
    ACCESS     read-only
    STATUS     mandatory
    DESCRIPTION
            "Interface up/down status."
    ::= {snPortMacSecurityEntry 6}

snPortMacSecurityShutdownTimeLeft OBJECT-TYPE
    SYNTAX     Unsigned32
    ACCESS     read-only
    STATUS     mandatory
    DESCRIPTION
            "If snPortMacSecurityShutdownStatus is up(1), this value will be 0.
            If snPortMacSecurityShutdownStatus is down(2), this gives
            the number of seconds before this interface is enabled again.
            In the later case, 0 means interface is permanently down."
    ::= {snPortMacSecurityEntry 7}

snPortMacSecurityVlanId OBJECT-TYPE
    SYNTAX     Unsigned32 (1..65535)
    ACCESS     read-only
    STATUS     mandatory
    DESCRIPTION
            "The vlan membership of this interface."
    ::= {snPortMacSecurityEntry 8}


--
-- Port Monitor Table
--

snPortMonitorTable OBJECT-TYPE
    SYNTAX     SEQUENCE OF PortMonitorEntry
    ACCESS     not-accessible
    STATUS     mandatory
    DESCRIPTION
            "Status of port monitoring on the device's interfaces."
    ::= { snPortMonitor 1 }

snPortMonitorEntry OBJECT-TYPE
    SYNTAX     PortMonitorEntry
    ACCESS     not-accessible
    STATUS     mandatory
    DESCRIPTION
            "An entry in the snPortMonitorTable"
    INDEX      { snPortMonitorIfIndex }
    ::= { snPortMonitorTable 1 }

PortMonitorEntry ::= SEQUENCE {
    snPortMonitorIfIndex                    InterfaceIndex,
    snPortMonitorMirrorList                 DisplayString
}

snPortMonitorIfIndex OBJECT-TYPE
    SYNTAX     InterfaceIndex
    ACCESS     not-accessible
    STATUS     mandatory
    DESCRIPTION
            "ifIndex value of the local interface on which
            monitoring is configuerd."
    ::= { snPortMonitorEntry 1 }

snPortMonitorMirrorList OBJECT-TYPE
     SYNTAX  DisplayString
     ACCESS  read-write
     STATUS  mandatory
     DESCRIPTION
             "Lists the monitoring configuration of this port.
             The value is a space delimited sequence of ifIndex of mirror port
             and monitor mode. The values for mode can be -
             0 -  off, 1 - input, 2 - output, 3 - both
             Eg. '65 2 66 1' means send the output traffic to port 2/1 and
             input traffic to port 2/2.
              To turn off a mirror use monitor mode of 0 (off) in the list."
     ::= { snPortMonitorEntry 2 }

END
FOUNDRY-SN-VSRP-MIB DEFINITIONS ::= BEGIN
-- Foundry SnRouter Group MIB Release 1.0.0
-- Revision 1 6/5/02
-- Revision 2 08/15/02
-- Copyright 1996-97 Foundry Networks, Inc.
-- All rights reserved.
-- This Foundry Networks SNMP Management Information Base 
-- Specification embodies Foundry Networks' confidential and
-- proprietary intellectual property. Foundry Networks retains all
-- title and ownership in the Specification, including any
-- revisions.

-- This Specification is supplied "AS IS," and Foundry Networks makes
-- no warranty, either express or implied, as to the use,
-- operation, condition, or performance of the Specification.

-- SECTION 1: Top Level Definitions
-- Imports

IMPORTS

	Counter FROM RFC1155-SMI 
	IpAddress, Counter	FROM RFC1155-SMI 

	snVsrp	FROM FOUNDRY-SN-SWITCH-GROUP-MIB;
		
	MacAddress ::=
	      OCTET STRING (SIZE(6))
	  -- This data type is used to model media addresses.  For many
	  -- types of media, this will be in a binary representation.
	  -- For example, an ethernet address would be represented as
	  -- a string of 6 octets.

snVsrpGlobal 	OBJECT IDENTIFIER ::= { snVsrp 1 } 
snVsrpIfIntf 	OBJECT IDENTIFIER ::= { snVsrp 2 }
snVsrpVirRtr 	OBJECT IDENTIFIER ::= { snVsrp 3 }

--  Section 1:	VSRP Global Variables

snVsrpGroupOperModeVsrp OBJECT-TYPE 
    SYNTAX  INTEGER 
        {   disabled(0),             
		    enabled(1)
		} 
	ACCESS  read-write
	STATUS  mandatory
	DESCRIPTION "The VSRP is configured on this system either enabled or 
        disabled and thedefault is disabled mode.
		 disabled(0)..........disable VSRP   
		 enabled(1)...........activate VSRP" 
	::= { snVsrpGlobal 1 } 
	
snVsrpIfStateChangeTrap OBJECT-TYPE
	SYNTAX	INTEGER { disabled(0), enabled(1) }
	ACCESS	read-write
	STATUS	mandatory
	DESCRIPTION
		"Indicates whether the SNMP agent process is
		permitted to generate VSRP interface state change
		traps."
    DEFVAL { enabled }
	::= { snVsrpGlobal 2 }

snVsrpIfMaxNumVridPerIntf OBJECT-TYPE
	SYNTAX	INTEGER
	ACCESS	read-only
	STATUS	mandatory
	DESCRIPTION
		"Indicates the maximum number of VRID per interface."
	::= { snVsrpGlobal 3 }

snVsrpIfMaxNumVridPerSystem OBJECT-TYPE
	SYNTAX	INTEGER
	ACCESS	read-only
	STATUS	mandatory
	DESCRIPTION
		"Indicates the maximum number of VRID per system."
	::= { snVsrpGlobal 4 }

snVsrpClearVrrpStat OBJECT-TYPE
	SYNTAX	INTEGER { normal(0), clear(1) }
	ACCESS	read-write
	STATUS	mandatory
	DESCRIPTION
		"Clear VSRP statistics command."
	::= { snVsrpGlobal 5 }

	 
--  Section 2:	VSRP  Interface Table, new table with vlan_id as an index, 

snVsrpIfTable OBJECT-TYPE
    SYNTAX   SEQUENCE OF SnVsrpIfEntry
    ACCESS   not-accessible
    STATUS   mandatory
    DESCRIPTION
       "The VSRP Interface Table describes the interfaces from
        the viewpoint of VSRP."
    ::= { snVsrpIfIntf 1 }

     snVsrpIfEntry OBJECT-TYPE
         SYNTAX   SnVsrpIfEntry
         ACCESS   not-accessible
         STATUS   mandatory
         DESCRIPTION
            "The VSRP Interface Entry describes one interface from
            the viewpoint of VSRP."
         INDEX { snVsrpIfVlanId}
         ::= { snVsrpIfTable 1 }

     SnVsrpIfEntry ::=
         SEQUENCE {
             snVsrpIfVlanId
 		 		INTEGER,
             snVsrpIfAuthType
			     INTEGER,
			 snVsrpIfAuthPassword
			     OCTET STRING
         }

     snVsrpIfVlanId OBJECT-TYPE
 		 SYNTAX  INTEGER
 		 ACCESS  read-only
 		 STATUS  mandatory
         DESCRIPTION
            "Vlan index."
         ::= { snVsrpIfEntry 1 }

    snVsrpIfAuthType OBJECT-TYPE
         SYNTAX   INTEGER { 
         				noAuth(0), 
         				simpleTextPasswd(1), 
						ipAuthHeader(2)
						}
         ACCESS   read-write
         STATUS   mandatory
         DESCRIPTION
            "The authentication type of this interface."
         ::= { snVsrpIfEntry 2 }

    snVsrpIfAuthPassword OBJECT-TYPE
		 SYNTAX	  OCTET STRING (SIZE (0..7))
         ACCESS   read-write
         STATUS   mandatory
         DESCRIPTION
            "The simple text password is allowed if only if 
            the snVsrpIfAuthType type is simpleTextPasswd."
         ::= { snVsrpIfEntry 3 }

	 
--  Section 3: VSRP Virtual Router Configuration Table
--  The vsrp Virtual Router Table augments with vsrp specific information.

snVsrpVirRtrTable OBJECT-TYPE
    SYNTAX   SEQUENCE OF SnVsrpVirRtrEntry
    ACCESS   not-accessible
    STATUS   mandatory
    DESCRIPTION
       "The vsrp virtual router Entry describes one virtual router from
        the viewpoint of vsrp."
    ::= { snVsrpVirRtr 1 }

     snVsrpVirRtrEntry OBJECT-TYPE
         SYNTAX   SnVsrpVirRtrEntry
         ACCESS   not-accessible
         STATUS   mandatory
         DESCRIPTION
            "The vsrp virtual router Entry describes one virtual router from
            the viewpoint of vsrp."
         INDEX { snVsrpVirRtrVlanId, snVsrpVirRtrId }
         ::= { snVsrpVirRtrTable 1 }

     SnVsrpVirRtrEntry ::=
         SEQUENCE {
              snVsrpVirRtrVlanId
 		 		INTEGER,
             snVsrpVirRtrId
			     INTEGER,
             snVsrpVirRtrOwnership
			     INTEGER,
             snVsrpVirRtrCfgPriority
                 INTEGER,
             snVsrpVirRtrTrackPriority
                 INTEGER,
             snVsrpVirRtrCurrPriority
                 INTEGER,
			 snVsrpVirRtrHelloInt 
				 INTEGER,
			 snVsrpVirRtrDeadInt 
				 INTEGER,
			 snVsrpVirRtrPreemptMode 
				 INTEGER,
			 snVsrpVirRtrState
				 INTEGER,
			snVsrpVirRtrIpAddrMask
				OCTET STRING,
			 snVsrpVirRtrActivate 
				 INTEGER,
             snVsrpVirRtrTrackPortList
                 OCTET STRING,
			 snVsrpVirRtrAdvertiseBackup 
				 INTEGER,
			 snVsrpVirRtrHoldDownInt 
				 INTEGER,
			 snVsrpVirRtrInitTtl
				 INTEGER,
             snVsrpVirRtrIncPortList
                 OCTET STRING,
			 snVsrpVirRtrSave
				 INTEGER,
			 snVsrpVirRtrBackupInt
				 INTEGER,
			 snVsrpVirRtrRowStatus 
				 INTEGER,
			 snVsrpVirRtrRxArpPktDropCnts 
				 Counter,
			 snVsrpVirRtrRxIpPktDropCnts 
				 Counter,
			 snVsrpVirRtrRxPortMismatchCnts 
				 Counter,
			 snVsrpVirRtrRxNumOfIpMismatchCnts 
				 Counter,				 
			 snVsrpVirRtrRxIpMismatchCnts 
				 Counter,
			 snVsrpVirRtrRxHelloIntMismatchCnts 
				 Counter,
			 snVsrpVirRtrRxPriorityZeroFromMasterCnts 
				 Counter,
			 snVsrpVirRtrRxHigherPriorityCnts 
				 Counter,
			 snVsrpVirRtrTransToMasterStateCnts 
				 Counter,
			 snVsrpVirRtrTransToBackupStateCnts 
				 Counter,
			 snVsrpVirRtrCurrDeadInt 
				 INTEGER,
			 snVsrpVirRtrCurHelloInt 
				 INTEGER,
			 snVsrpVirRtrCurHoldDownInt 
				 INTEGER,
			 snVsrpVirRtrCurInitTtl
				 INTEGER,
			snVsrpVirRtrHelloMacAddress
				MacAddress,
		    snVsrpVirRtrMasterIpAddr
				 IpAddress
       }
       
     snVsrpVirRtrVlanId OBJECT-TYPE
 		 SYNTAX  INTEGER
 		 ACCESS  read-only
 		 STATUS  mandatory
         DESCRIPTION
            "Vlan index."
         ::= { snVsrpVirRtrEntry 1 }
         
    snVsrpVirRtrId OBJECT-TYPE
         SYNTAX   INTEGER (1..255)
         ACCESS   read-only
         STATUS   mandatory
         DESCRIPTION
            "One of the virtual router ID of this vsrp interface."
         ::= { snVsrpVirRtrEntry 2 }

    snVsrpVirRtrOwnership OBJECT-TYPE
	     SYNTAX   INTEGER {
					incomplete(0),
					owner(1),
					backup(2)
					}
         ACCESS   read-write
         STATUS   mandatory
         DESCRIPTION
            "The ownership of this vsrp router interface 
            can be set to backup(2).  
            VirRtr SNMP-GET returns incomplete(0), it means 
            no IP address has assigned to this vsrp router interface."
         ::= { snVsrpVirRtrEntry 3 }

     snVsrpVirRtrCfgPriority OBJECT-TYPE
         SYNTAX   INTEGER (1..254)
         ACCESS   read-write
         STATUS   mandatory
         DESCRIPTION
            "The higher the number the higher the priority is.
            This parameter decides which backup router should becomes
            the Active Router for the interface.  A backup Router with
            higher priority selected to becomes the Active Router.
            Therefore, this Object can be set if only if snVsrpVirRtrOwnership
            is set to backup(2)."
         DEFVAL { 100 }
         ::= { snVsrpVirRtrEntry 4 }

     snVsrpVirRtrTrackPriority OBJECT-TYPE
         SYNTAX   INTEGER (1..254)
         ACCESS   read-write
         STATUS   mandatory
         DESCRIPTION
            "The higher the number the higher the priority is.
            after this object is configured, the snVsrpVirRtrCurrPriority 
            of this interface will be adjusted dynamically with this
			track priority when the Track Port states first
            changes from UP to DOWN."
         ::= { snVsrpVirRtrEntry 5 }

     snVsrpVirRtrCurrPriority OBJECT-TYPE
         SYNTAX   INTEGER (1..254)
         ACCESS   read-only
         STATUS   mandatory
         DESCRIPTION
            "The higher the number the higher the priority is.
            This object will be adjusted dynamically with the
			track priority when the Track Port states first
            changes from UP to DOWN."
         ::= { snVsrpVirRtrEntry 6 }

     snVsrpVirRtrHelloInt OBJECT-TYPE
         SYNTAX   INTEGER (1..84)
         ACCESS   read-write
         STATUS   mandatory
         DESCRIPTION
            "Time interval between advertisements (seconds)."
         DEFVAL { 1 }
         ::= { snVsrpVirRtrEntry 7 }

     snVsrpVirRtrDeadInt OBJECT-TYPE
         SYNTAX   INTEGER (0..84)
         ACCESS   read-write
         STATUS   mandatory
         DESCRIPTION
            "Dead interval (seconds)."
         DEFVAL { 1 }
         ::= { snVsrpVirRtrEntry 8 }

     snVsrpVirRtrPreemptMode OBJECT-TYPE
         SYNTAX   INTEGER { disabled(0), enabled(1) }
         ACCESS   read-write
         STATUS   mandatory
         DESCRIPTION
            "This mode controls whether a higher priority Backup router
            preempts a lower priority Master.  The mode with enabled(1)
            allow preemption and disabled(0) prohibit preemption."
         DEFVAL { enabled }
         ::= { snVsrpVirRtrEntry 9 }

	 snVsrpVirRtrState OBJECT-TYPE
	     SYNTAX   INTEGER {
					init(0),
					master(1),
					backup(2)
				  }
         ACCESS   read-only
         STATUS   mandatory
         DESCRIPTION
            "This object specifies the vsrp Router's interface state as:
            init(0)...initialization state.
            master(1)...master state.
            backup(2)...backup state."
         ::= { snVsrpVirRtrEntry 10 }

    snVsrpVirRtrIpAddrMask OBJECT-TYPE
		 SYNTAX  OCTET STRING (SIZE(64))
         ACCESS   read-write
         STATUS   mandatory
         DESCRIPTION
            "The numbers of IP Addresses of this virtual router of this 
            interface, this holds good for L3 vsrp."
         ::= { snVsrpVirRtrEntry 11 }

	 snVsrpVirRtrActivate OBJECT-TYPE
	     SYNTAX   INTEGER {
					disabled(0),
					enabled(1)
				  }
         ACCESS   read-write
         STATUS   mandatory
         DESCRIPTION
            "This object specifies the vsrp Router's activate command as:
            disabled(0)...deactivate this vsrp Router.
            enabled(1)....activate this vsrp Router."
         ::= { snVsrpVirRtrEntry 12 }

     snVsrpVirRtrTrackPortList OBJECT-TYPE
		 SYNTAX  OCTET STRING
         ACCESS   read-write
         STATUS   mandatory
         DESCRIPTION
            "This object specifies the identity of the physical port and virtual ports
			whose state is to be monitored.  Each port index is 
			an ifIndex, if there are consecutive 4 or more ifIndex then
			they will be encoded like below. 
            Encoding and decoding scheme is range based:
            Each range prefix with 0000 (2 octets) where 0000 is not valid 
            ifIndex. Next 2 octets indicates lower range ifIndex, followed by 2 
            octets of higher range ifIndex. Individual(non range) ones will be displayed as it is.
            Ex:
            port list: 0001..0005 0015 0032..0047
            Port list in PDU:  0000 0001 0005 000f 0000 0020 002f.
			If this object is configured
			then the Preference Level of this interface will be adjusted
			dynamically depending on the state of the Track Port.
            The interface's Preference Level is reduced by value of 
            Preference Level parameter when the Track Port states first
            changes from UP to DOWN.  When the Track Port next comes up
            the interface's Preference Level is increased by the amount
            specified by the Preference Level.
            The router VSRP physical track port membership."
         ::= { snVsrpVirRtrEntry 13 }

     snVsrpVirRtrAdvertiseBackup OBJECT-TYPE
         SYNTAX   INTEGER { disabled(0), enabled(1) }
         ACCESS   read-write
         STATUS   mandatory
         DESCRIPTION
            "Set Advertise this backup router to master "
         DEFVAL { disabled }
         ::= { snVsrpVirRtrEntry 14 }			  
         
	snVsrpVirRtrHoldDownInt OBJECT-TYPE
         SYNTAX   INTEGER (1..84)
         ACCESS   read-write
         STATUS   mandatory
         DESCRIPTION
            "VSRP protection mechanism, an extra delay for a switch in
            backup mode to upgrade itself to master mode"
         DEFVAL { 2 }
         ::= { snVsrpVirRtrEntry 15 }

     snVsrpVirRtrInitTtl OBJECT-TYPE
         SYNTAX   INTEGER (1..255)
         ACCESS   read-write
         STATUS   mandatory
         DESCRIPTION
            "VSRP:TTL in the hello packet to regulate the distance that a hello packet 
            can travel. It prevents the flooding of VSRP hello packets in the network"
         DEFVAL { 2 }
         ::= { snVsrpVirRtrEntry 16 }

     snVsrpVirRtrIncPortList OBJECT-TYPE
		 SYNTAX  OCTET STRING
         ACCESS   read-write
         STATUS   mandatory
         DESCRIPTION
            "Include all free ports of the VLAN into its control ports"
         ::= { snVsrpVirRtrEntry 17 }

     snVsrpVirRtrSave OBJECT-TYPE
         SYNTAX   INTEGER { disabled(0), enabled(1) }
         ACCESS   read-write
         STATUS   mandatory
         DESCRIPTION
            "Set VSRP to save current parameters value"
         DEFVAL { disabled }
         ::= { snVsrpVirRtrEntry 18 }

     snVsrpVirRtrBackupInt OBJECT-TYPE
         SYNTAX   INTEGER (60..3600)
         ACCESS   read-write
         STATUS   mandatory
         DESCRIPTION
            "Time interval between backup routers hello message advertisements (seconds)."
         DEFVAL { 60 }
         ::= { snVsrpVirRtrEntry 19 }
         
    snVsrpVirRtrRowStatus OBJECT-TYPE
	     SYNTAX   INTEGER {
					invalid(1),
					valid(2),
					delete(3),
					create(4),
					modify(5)
				  }
		 ACCESS   read-write
	     STATUS   mandatory
		 DESCRIPTION
		 	"This object is used to create and
		     delete row in the table and control
			 if they are used. The values
		     that can be written are:
		     delete(3)...deletes the row
		     create(4)...creates a new row
		     modify(5)...modifies an existing row

		     VirRtr the row exists, then a SET with
		     value of create(4) returns error
		     'badValue'. Deleted rows go away
		     immediately. The following values
		     can be returned on reads:
		     noSuch(0)...no such row
		     invalid(1)...Setting it to 'invalid' has the effect of
                          rendering it inoperative..
		     valid(2)....the row exists and is valid"
	     ::= { snVsrpVirRtrEntry 20}

	 snVsrpVirRtrRxArpPktDropCnts OBJECT-TYPE
	     SYNTAX   Counter
         ACCESS   read-only
         STATUS   mandatory
         DESCRIPTION
            "The received vsrp ARP Packet Drop Counts."
         ::= { snVsrpVirRtrEntry 21 }

	 snVsrpVirRtrRxIpPktDropCnts OBJECT-TYPE
	     SYNTAX   Counter
         ACCESS   read-only
         STATUS   mandatory
         DESCRIPTION
            "The received VSRP IP Packet Drop Counts."
         ::= { snVsrpVirRtrEntry 22 }

	 snVsrpVirRtrRxPortMismatchCnts OBJECT-TYPE
	     SYNTAX   Counter
         ACCESS   read-only
         STATUS   mandatory
         DESCRIPTION
            "The received vsrp Port mismatching Counts."
         ::= { snVsrpVirRtrEntry 23 }

	 snVsrpVirRtrRxNumOfIpMismatchCnts OBJECT-TYPE
	     SYNTAX   Counter
         ACCESS   read-only
         STATUS   mandatory
         DESCRIPTION
            "The received VSRP Number of IP Addresses mismatching Counts."
         ::= { snVsrpVirRtrEntry 24 }

	 snVsrpVirRtrRxIpMismatchCnts OBJECT-TYPE
	     SYNTAX   Counter
         ACCESS   read-only
         STATUS   mandatory
         DESCRIPTION
            "The received vsrp IP Address mismatching Counts."
         ::= { snVsrpVirRtrEntry 25 }

	 snVsrpVirRtrRxHelloIntMismatchCnts OBJECT-TYPE
	     SYNTAX   Counter
         ACCESS   read-only
         STATUS   mandatory
         DESCRIPTION
  			"The counts of the virtual router interface with hello interval mismatch counts."
         ::= { snVsrpVirRtrEntry 26 }

	 snVsrpVirRtrRxPriorityZeroFromMasterCnts OBJECT-TYPE
	     SYNTAX   Counter
         ACCESS   read-only
         STATUS   mandatory
         DESCRIPTION
  			"The counts of the virtual router interface with Priority zero from the master."
         ::= { snVsrpVirRtrEntry 27 }

	 snVsrpVirRtrRxHigherPriorityCnts OBJECT-TYPE
	     SYNTAX   Counter
         ACCESS   read-only
         STATUS   mandatory
         DESCRIPTION
  			"The counts of the virtual router interface with higher Priority."
         ::= { snVsrpVirRtrEntry 28 }

	 snVsrpVirRtrTransToMasterStateCnts OBJECT-TYPE
	     SYNTAX   Counter
         ACCESS   read-only
         STATUS   mandatory
         DESCRIPTION
  			"The counts of the virtual router interface transition to master state."
         ::= { snVsrpVirRtrEntry 29 }

	 snVsrpVirRtrTransToBackupStateCnts OBJECT-TYPE
	     SYNTAX   Counter
         ACCESS   read-only
         STATUS   mandatory
         DESCRIPTION
  			"The counts of the virtual router interface transition to backup state."
         ::= { snVsrpVirRtrEntry 30 }

     snVsrpVirRtrCurrDeadInt OBJECT-TYPE
         SYNTAX   INTEGER 
         ACCESS   read-only
         STATUS   mandatory
         DESCRIPTION
            "Current Dead interval (in 100 milliseconds)."
         ::= { snVsrpVirRtrEntry 31 }

	snVsrpVirRtrCurHelloInt OBJECT-TYPE
         SYNTAX   INTEGER (1..84)
         ACCESS   read-only
         STATUS   mandatory
         DESCRIPTION
            "Set backup router hello interval"
         ::= { snVsrpVirRtrEntry 32 }

	snVsrpVirRtrCurHoldDownInt OBJECT-TYPE
         SYNTAX   INTEGER (1..84)
         ACCESS   read-only
         STATUS   mandatory
         DESCRIPTION
            "VSRP protection mechanism, an extra delay for a switch in
            backup mode to upgrade itself to master mode"
         ::= { snVsrpVirRtrEntry 33 }

     snVsrpVirRtrCurInitTtl OBJECT-TYPE
         SYNTAX   INTEGER (1..255)
         ACCESS   read-only
         STATUS   mandatory
         DESCRIPTION
            "VSRP:TTL in the hello packet to regulate the distance that a hello packet 
            can travel. It prevents the flooding of VSRP hello packets in the network"
         ::= { snVsrpVirRtrEntry 34 }

	snVsrpVirRtrHelloMacAddress    OBJECT-TYPE
		SYNTAX  MacAddress
		ACCESS  read-only
		STATUS  mandatory
		DESCRIPTION
			"Hello MAC address."
		::= { snVsrpVirRtrEntry 35 }

     snVsrpVirRtrMasterIpAddr OBJECT-TYPE
         SYNTAX       IpAddress
         ACCESS       read-only
         STATUS       mandatory
         DESCRIPTION
             "The master router's real/virtual (primary) IP address. This is
             the IP address listed as the source in vsrp advertisement
             last received by this virtual router."
         ::= { snVsrpVirRtrEntry 36 }

		
END		
-- SECTION 1: Top Level Definitions


FOUNDRY-SN-RT-L3-SWITCH-GROUP-MIB DEFINITIONS ::= BEGIN


-- Foundry L3 Switch Group MIB Release 1.0.0
-- Revision 0 11/16/96

-- Copyright 1996-97 Foundry Networks, Inc.
-- All rights reserved.
-- This Foundry Networks SNMP Management Information Base Specification
-- (Specification) embodies Foundry Networks' confidential and
-- proprietary intellectual property. Foundry Networks retains all
-- title and ownership in the Specification, including any
-- revisions.

-- This Specification is supplied "AS IS," and Foundry Networks makes
-- no warranty, either express or implied, as to the use,
-- operation, condition, or performance of the Specification.


-- Imports

IMPORTS
	IpAddress, Counter, TimeTicks
		FROM RFC1155-SMI
	OBJECT-TYPE             
		FROM RFC-1212
	snIpx, snIp
		FROM FOUNDRY-SN-ROOT-MIB;

		-- textual conventions
	  -- maximum of ports are 32.  

	--  Row Creation/Deletion Values

	     RowSts ::= INTEGER { other(1),
						valid(2),
						delete(3),
						create(4)
						}
	--  RtrStatus Values

	     RtrStatus ::= INTEGER { disabled(0), enabled(1) }

	--  Clear Status Values

	     ClearStatus ::= INTEGER { normal(0), clear(1) }

	--  Port index

	     PortIndex ::= INTEGER (1..34)

	--  Action 

		Action ::= INTEGER { deny(0), permit(1) }

        PhysAddress ::= OCTET STRING
    -- This data type is used to model media addresses.  For many
    -- types of media, this will be in a binary representation.
    -- For example, an ethernet address would be represented as
    -- a string of 6 octets.

    --  IPX Network Number

        NetNumber ::= OCTET STRING (SIZE(4))


-- IP general group

snRtIpGeneral               OBJECT IDENTIFIER ::= { snIp 1 }
		
snRtClearArpCache       OBJECT-TYPE
	SYNTAX  ClearStatus
	ACCESS  read-write
	STATUS  mandatory
	DESCRIPTION
		"clear(1) will clear arp cache table."
	::= { snRtIpGeneral 1 }

snRtClearIpCache                OBJECT-TYPE
	SYNTAX  ClearStatus
	ACCESS  read-write
	STATUS  mandatory
	DESCRIPTION
		"clear(1) will clear ip route cache table."
	::= { snRtIpGeneral 2 }

-- L3 ip filter table

snRtIpFilterTable       OBJECT-TYPE
	SYNTAX  SEQUENCE OF SnRtIpFilterEntry
	ACCESS  not-accessible
	STATUS  mandatory
	DESCRIPTION
		"IP filter table."
	::= { snIp 3 }

snRtIpFilterEntry       OBJECT-TYPE
	SYNTAX  SnRtIpFilterEntry
	ACCESS  not-accessible
	STATUS  mandatory
	DESCRIPTION
		"An entry in the IP filter table."
	INDEX   { snRtIpFilterIndex }
	::= { snRtIpFilterTable 1 }

SnRtIpFilterEntry ::= SEQUENCE {
	snRtIpFilterIndex
		INTEGER,
	snRtIpFilterAction              
		INTEGER,
	snRtIpFilterProtocol            
		INTEGER,
	snRtIpFilterSourceIp
		IpAddress,
	snRtIpFilterSourceMask
		IpAddress,
	snRtIpFilterDestIp
		IpAddress,
	snRtIpFilterDestMask
		IpAddress,
	snRtIpFilterOperator
		INTEGER,
	snRtIpFilterOperand
		INTEGER,
	snRtIpFilterRowStatus
		RowSts,
	snRtIpFilterEstablished
		RtrStatus,
	snRtIpFilterQosPriority
		INTEGER
	}

snRtIpFilterIndex       OBJECT-TYPE
	SYNTAX  INTEGER (1..1024)
	ACCESS  read-only
	STATUS  mandatory
	DESCRIPTION
		"The table index for a filter entry."
	::= { snRtIpFilterEntry 1 }

snRtIpFilterAction      OBJECT-TYPE
	SYNTAX  INTEGER { deny(0), permit(1), qosEnabled(2) } 
	ACCESS  read-write
	STATUS  mandatory
	DESCRIPTION
		"Action to take if the ip packet match
		with this filter."
	::= { snRtIpFilterEntry 2 }

snRtIpFilterProtocol    OBJECT-TYPE
	SYNTAX  INTEGER (0..255)
	ACCESS  read-write
	STATUS  mandatory
	DESCRIPTION
		"Transport protocol. 0 means don't care"
	::= { snRtIpFilterEntry 3 }

snRtIpFilterSourceIp    OBJECT-TYPE
	SYNTAX  IpAddress
	ACCESS  read-write
	STATUS  mandatory
	DESCRIPTION
		"Source IP address."
	::= { snRtIpFilterEntry 4 }

snRtIpFilterSourceMask  OBJECT-TYPE
	SYNTAX  IpAddress
	ACCESS  read-write
	STATUS  mandatory
	DESCRIPTION
		"Source IP subnet mask."
	::= { snRtIpFilterEntry 5 }

snRtIpFilterDestIp      OBJECT-TYPE
	SYNTAX  IpAddress
	ACCESS  read-write
	STATUS  mandatory
	DESCRIPTION
		"Destination IP address."
	::= { snRtIpFilterEntry 6 }

snRtIpFilterDestMask    OBJECT-TYPE
	SYNTAX  IpAddress
	ACCESS  read-write
	STATUS  mandatory
	DESCRIPTION
		"Destination IP subnet mask."
	::= { snRtIpFilterEntry 7 }

snRtIpFilterOperator    OBJECT-TYPE
	SYNTAX  INTEGER { greater(1), equal(2), less(3), notEqual(4) }
	ACCESS  read-write
	STATUS  mandatory
	DESCRIPTION
		"Type of comparison to perform.
		for now, this only applys to tcp or udp
		to compare the port number"
	::= { snRtIpFilterEntry 8 }

snRtIpFilterOperand     OBJECT-TYPE
	SYNTAX  INTEGER(0..65535)
	ACCESS  read-write
	STATUS  mandatory
	DESCRIPTION
		"For now this only refers to transport 
		protocol port number. 0 means NA"
	::= { snRtIpFilterEntry 9 }

snRtIpFilterRowStatus   OBJECT-TYPE
	SYNTAX  RowSts
	ACCESS  read-write
	STATUS  mandatory
	DESCRIPTION
		"To create or delete a filter
		entry."
	::= { snRtIpFilterEntry 10 }

snRtIpFilterEstablished OBJECT-TYPE
	SYNTAX  RtrStatus
	ACCESS  read-write
	STATUS  mandatory
	DESCRIPTION
		"Enable/Disable the filtering of established TCP
		packets of which the ACK or RESET flag is on. This
		additional filter only applies to TCP transport
		protocol."
	::= { snRtIpFilterEntry 11 }

snRtIpFilterQosPriority OBJECT-TYPE
	SYNTAX  INTEGER {
		level0(0),
		level1(1),
		level2(2),
		level3(3),
		level4(4),
		level5(5),
		level6(6),
		level7(7)
		}
	ACCESS  read-write
	STATUS  mandatory
	DESCRIPTION
		"The router L4 Qos Priority values are:
		 low(0)   -- low prority
		 high(1) -- high prority.
		 The Priority values are:
		level0(0), level1(1), level2(2), level3(3),
		level4(4), level5(5), level6(6), level7(7) "
	::= { snRtIpFilterEntry 12 }

-- Trace route group
-- This group uses the following method to detect routes used to reach
-- a destination address. The originating router sends a probe packet
-- (a UDP packet) to the destination address with TTL of 1. The first
-- router that receives this packet decrements the TTL, then drops the
-- packet and returns a ICMP packet to the originator. The originating
-- router records the route in snRtIpTraceRouteResultTable. The ori-
-- ginating router sends a probe packet (a UDP packet) to the des-
-- tination address with TTL of 2. The second router that receives
-- this packet decrements the TTL, then drops the packet and returns
-- a ICMP packet to the originator. The originating router records the
-- route in snRtIpTraceRouteResultTable. This procedure is repeated
-- until the destination is reached, or the maximum TTL is reached.

snRtIpTraceRoute            OBJECT IDENTIFIER ::= { snIp 10 }
snRtIpTraceRouteGeneral     OBJECT IDENTIFIER ::= { snRtIpTraceRoute 1 }
snRtIpTraceRouteResult      OBJECT IDENTIFIER ::= { snRtIpTraceRoute 2 }

-- General trace route group

snRtIpTraceRouteTargetAddr  OBJECT-TYPE
	SYNTAX  IpAddress
	ACCESS  read-write
	STATUS  mandatory
	DESCRIPTION
		"Target IP address of which trace route is performed."
	::= { snRtIpTraceRouteGeneral 1 }

snRtIpTraceRouteMinTtl      OBJECT-TYPE
	SYNTAX  INTEGER (0..255)
	ACCESS  read-write
	STATUS  mandatory
	DESCRIPTION
		"Minimum TTL value carried in the first probe packet.
		Value 0 cannot be used for SET operations. This value
		is returned if traceroute is not running within the system."
    DEFVAL { 1 }
	::= { snRtIpTraceRouteGeneral 2 }

snRtIpTraceRouteMaxTtl      OBJECT-TYPE
	SYNTAX  INTEGER (0..255)
	ACCESS  read-write
	STATUS  mandatory
	DESCRIPTION
		"Maximum TTL value carried in the last probe packet.
		Value 0 cannot be used for SET operations. This value
		is returned if traceroute is not running within the system."
    DEFVAL { 30 }
	::= { snRtIpTraceRouteGeneral 3 }

snRtIpTraceRouteTimeOut     OBJECT-TYPE
	SYNTAX  INTEGER (0..120)
	ACCESS  read-write
	STATUS  mandatory
	DESCRIPTION
		"Time out period (in seconds) to wait for the response
		from the probe packet (i,e, the ICMP packet).
		Value 0 cannot be used for SET operations. This value
		is returned if traceroute is not running within the system."
    DEFVAL { 2 }
	::= { snRtIpTraceRouteGeneral 4 }

snRtIpTraceRouteControl     OBJECT-TYPE
	SYNTAX  INTEGER {
				start(1),
				abort(2),
				success(3),
				failure(4),
				inProgress(5)
			}
	ACCESS  read-write
	STATUS  mandatory
	DESCRIPTION
		"Only 'start' and 'abort' are writable values; 'success',
		'failure' and 'inProgress' are readeable (or returned)
		values.
		
		Writing 'start' to this object to initiate the trace route
		operation. snRtIpTraceRouteDestAddr must have been init-
		ialized before 'start' is writen.

		This object will return 'inProgress' after trace route
		operation has started. During the 'inProgress' state,
		writing 'abort' to this object will stop the current
		trace route operation.

		If the destination address is reached, this object
		returned 'success'. snRtIpTraceRouteResultTable
		contains the routes (and the target address) to
		reach the destination address. If the destination
		address does not reach, timeout, or ending TTL
		reached, 'failure' is returned."
	::= { snRtIpTraceRouteGeneral 5 }

-- Trace route result table

snRtIpTraceRouteResultTable  OBJECT-TYPE
	SYNTAX  SEQUENCE OF SnRtIpTraceRouteResultEntry
	ACCESS  not-accessible
	STATUS  mandatory
	DESCRIPTION
		"Trace route result table."
	::= { snRtIpTraceRouteResult 1 }

snRtIpTraceRouteResultEntry  OBJECT-TYPE
	SYNTAX  SnRtIpTraceRouteResultEntry
	ACCESS  not-accessible
	STATUS  mandatory
	DESCRIPTION
		"An entry of the trace route result table."
	INDEX   { snRtIpTraceRouteResultIndex }
	::= { snRtIpTraceRouteResultTable 1 }

SnRtIpTraceRouteResultEntry ::= SEQUENCE {
	snRtIpTraceRouteResultIndex
		INTEGER,
	snRtIpTraceRouteResultAddr
		IpAddress,
	snRtIpTraceRouteResultRoundTripTime1
		TimeTicks,
	snRtIpTraceRouteResultRoundTripTime2
		TimeTicks
	}

snRtIpTraceRouteResultIndex          OBJECT-TYPE
	SYNTAX  INTEGER
	ACCESS  read-only
	STATUS  mandatory
	DESCRIPTION
		"The table index for a trace route result entry."
	::= { snRtIpTraceRouteResultEntry 1 }

snRtIpTraceRouteResultAddr           OBJECT-TYPE
	SYNTAX  IpAddress
	ACCESS  read-only
	STATUS  mandatory
	DESCRIPTION
		"The router or the target address of which forms
		part of the route to reach the destination address."
	::= { snRtIpTraceRouteResultEntry 2 }

snRtIpTraceRouteResultRoundTripTime1 OBJECT-TYPE
	SYNTAX  TimeTicks
	ACCESS  read-only
	STATUS  mandatory
	DESCRIPTION
		"The round trip time between the first probe packet
		transmitted and the reponse ICMP packet received."
	::= { snRtIpTraceRouteResultEntry 3 }

snRtIpTraceRouteResultRoundTripTime2 OBJECT-TYPE
	SYNTAX  TimeTicks
	ACCESS  read-only
	STATUS  mandatory
	DESCRIPTION
		"The round trip time between the second probe packet
		transmitted and the reponse ICMP packet received."
	::= { snRtIpTraceRouteResultEntry 4 }

-- L3 ipx filter table
-- IPX Forward Filter table
snIpxGen			OBJECT IDENTIFIER ::= { snIpx 1 }
snIpxCache			OBJECT IDENTIFIER ::= { snIpx 2 }
snIpxRoute			OBJECT IDENTIFIER ::= { snIpx 3 }
snIpxFwdFilter		OBJECT IDENTIFIER ::= { snIpx 5 }
snIpxPortCounters	OBJECT IDENTIFIER ::= { snIpx 12 }

-- IPX General MIBs

                
snIpxClearCache 		OBJECT-TYPE
	SYNTAX  ClearStatus
	ACCESS  read-write
	STATUS  mandatory
	DESCRIPTION
		"clear(1) will clear cache table."
	::= { snIpxGen 3 }

snIpxClearRoute 		OBJECT-TYPE
	SYNTAX  ClearStatus
	ACCESS  read-write
	STATUS  mandatory
	DESCRIPTION
		"clear(1) will clear ipx route table."
	::= { snIpxGen 4 }

snIpxClearTrafficCnts		OBJECT-TYPE
	SYNTAX  ClearStatus
	ACCESS  read-write
	STATUS  mandatory
	DESCRIPTION
		"clear(1) will clear ipx all traffic counters.
		 - snIpxRcvPktsCnt, snIpxFwdPktsCnt,
		   snIpxRcvDropPktsCnt, snIpxTxDropPktsCnt,
		   snIpxRcvFiltPktsCnt, snIpxTxFiltPktsCnt."
	::= { snIpxGen 5 }


snIpxRcvPktsCnt 		OBJECT-TYPE
	SYNTAX	Counter
	ACCESS	read-only
	STATUS  mandatory
	DESCRIPTION
		"IPX incoming packets counter."
	::= { snIpxGen 6 }


snIpxFwdPktsCnt 		OBJECT-TYPE
	SYNTAX	Counter
	ACCESS	read-only
	STATUS  mandatory
	DESCRIPTION
		"IPX forwarding packets counter."
	::= { snIpxGen 8 }

snIpxRcvFiltPktsCnt		OBJECT-TYPE
	SYNTAX	Counter
	ACCESS	read-only
	STATUS  mandatory
	DESCRIPTION
		"IPX receiving filter packets counter."
	::= { snIpxGen 10 }


-- IPX Cache table

snIpxCacheTable  OBJECT-TYPE
	SYNTAX	SEQUENCE OF SnIpxCacheEntry
	ACCESS  not-accessible
	STATUS  mandatory
	DESCRIPTION
		"IPX Cache table."
	::= { snIpxCache 1 }

snIpxCacheEntry  OBJECT-TYPE
	SYNTAX	SnIpxCacheEntry
	ACCESS  not-accessible
	STATUS  mandatory
	DESCRIPTION
		"An entry in the IPX Cache table."
	INDEX	{ snIpxCacheIndex }
	::= { snIpxCacheTable 1 }

SnIpxCacheEntry ::= SEQUENCE {
	snIpxCacheIndex
		INTEGER,
    snIpxCacheNetNum
        OCTET STRING,
    snIpxCacheNode
        PhysAddress,
    snIpxCacheOutFilter
        RtrStatus,
    snIpxCacheEncap  
        INTEGER,
	snIpxCachePort
		PortIndex
	}

snIpxCacheIndex  OBJECT-TYPE
	SYNTAX	INTEGER
	ACCESS  read-only
	STATUS  mandatory
	DESCRIPTION
		"The table index for a IPX Cache entry."
	::= { snIpxCacheEntry 1 }


snIpxCacheNetNum  OBJECT-TYPE
	SYNTAX	OCTET STRING (SIZE(2..16))
	ACCESS	read-only
	STATUS  mandatory
	DESCRIPTION
		"Cache Network number is represented by ASCII mainly for HP OpenView."
	::= { snIpxCacheEntry 2 }

snIpxCacheNode  OBJECT-TYPE
	SYNTAX	PhysAddress
	ACCESS  read-only
	STATUS  mandatory
	DESCRIPTION
		"Cache Node Number."
	::= { snIpxCacheEntry 3 }

snIpxCacheOutFilter	OBJECT-TYPE
	SYNTAX	RtrStatus
	ACCESS  read-only
	STATUS  mandatory
	DESCRIPTION
		"Cache Outbound Filter is ether disabled(0) or enabled(1)."
	::= { snIpxCacheEntry 4 }

snIpxCacheEncap  OBJECT-TYPE
	SYNTAX	 INTEGER {
	    ethernetII(1),
	    ethernet8022(2),
	    ethernet8023(3),
	    ethernetSnap(4)
	}
	ACCESS	read-only
	STATUS  mandatory
	DESCRIPTION
		"The IPX encapsulation frame type."
	::= { snIpxCacheEntry 5 }


snIpxCachePort  OBJECT-TYPE
	SYNTAX	PortIndex
	ACCESS	read-only
	STATUS  mandatory
	DESCRIPTION
		"IPX Router Port number." 
	::= { snIpxCacheEntry 6 }




-- IPX route table

snIpxRouteTable  OBJECT-TYPE
	SYNTAX	SEQUENCE OF SnIpxRouteEntry
	ACCESS  not-accessible
	STATUS  mandatory
	DESCRIPTION
		"IPX route table."
	::= { snIpxRoute 1 }

snIpxRouteEntry  OBJECT-TYPE
	SYNTAX	SnIpxRouteEntry
	ACCESS  not-accessible
	STATUS  mandatory
	DESCRIPTION
		"An entry in the IPX route table."
	INDEX	{ snIpxRouteIndex }
	::= { snIpxRouteTable 1 }

SnIpxRouteEntry ::= SEQUENCE {
	snIpxRouteIndex
		INTEGER,
	snIpxDestNetNum
		OCTET STRING,
	snIpxFwdRouterNode
		PhysAddress,
	snIpxDestHopCnts
		INTEGER,
	snIpxRouteMetric
		INTEGER,
	snIpxDestPort
	    INTEGER
	}

snIpxRouteIndex  OBJECT-TYPE
	SYNTAX	INTEGER
	ACCESS  read-only
	STATUS  mandatory
	DESCRIPTION
		"The table index for a IPX route entry."
	::= { snIpxRouteEntry 1 }

snIpxDestNetNum  OBJECT-TYPE
	SYNTAX	OCTET STRING (SIZE(2..16))
	ACCESS	read-only
	STATUS  mandatory
	DESCRIPTION
		"Destination Network number is represented by ASCII mainly for HP OpenView."
	::= { snIpxRouteEntry 2 }

snIpxFwdRouterNode  OBJECT-TYPE
	SYNTAX	PhysAddress
	ACCESS  read-only
	STATUS  mandatory
	DESCRIPTION
		"Forward Router Node Number."
	::= { snIpxRouteEntry 3 }

snIpxDestHopCnts  OBJECT-TYPE
	SYNTAX	INTEGER
	ACCESS	read-only
	STATUS  mandatory
	DESCRIPTION
		"Number of hops to reach the
		 destination."
	::= { snIpxRouteEntry 4 }

snIpxRouteMetric  OBJECT-TYPE
	SYNTAX  INTEGER
	ACCESS	read-only
	STATUS  mandatory
	DESCRIPTION
		"The metrics to next hop router."
	::= { snIpxRouteEntry 5 }

snIpxDestPort  OBJECT-TYPE
	SYNTAX  INTEGER
	ACCESS	read-only
	STATUS  mandatory
	DESCRIPTION
		"The destination port."
	::= { snIpxRouteEntry 6 }


snIpxFwdFilterTable	  OBJECT-TYPE
	SYNTAX	SEQUENCE OF SnIpxFwdFilterEntry
	ACCESS  not-accessible
	STATUS  mandatory
	DESCRIPTION
		"IPX Forward Filter table."
	::= { snIpxFwdFilter 1 }

snIpxFwdFilterEntry	  OBJECT-TYPE
	SYNTAX	SnIpxFwdFilterEntry
	ACCESS  not-accessible
	STATUS  mandatory
	DESCRIPTION
		"An entry in the IPX Forward Filter table."
	INDEX	{ snIpxFwdFilterId }
	::= { snIpxFwdFilterTable 1 }

SnIpxFwdFilterEntry ::= SEQUENCE {
	snIpxFwdFilterId
		INTEGER,
	snIpxFwdFilterAction
		Action,
	snIpxFwdFilterSocket
		INTEGER,
	snIpxFwdFilterSrcNet
		NetNumber,
	snIpxFwdFilterSrcNode
		PhysAddress,
	snIpxFwdFilterDestNet
		NetNumber,
	snIpxFwdFilterDestNode
		PhysAddress,
	snIpxFwdFilterRowStatus
		INTEGER
	}

snIpxFwdFilterId       OBJECT-TYPE
	SYNTAX	INTEGER
	ACCESS  read-only
	STATUS  mandatory
	DESCRIPTION
		"The filter ID for a filter entry."
	::= { snIpxFwdFilterEntry 1 }

snIpxFwdFilterAction	  OBJECT-TYPE
	SYNTAX  Action 
	ACCESS  read-write
	STATUS  mandatory
	DESCRIPTION
		"Action to take if the ipx packet match
		with this filter."
	::= { snIpxFwdFilterEntry 2 }

snIpxFwdFilterSocket	OBJECT-TYPE
	SYNTAX	INTEGER
	ACCESS  read-write
	STATUS  mandatory
	DESCRIPTION
		"IPX Forward Filter Socket Number."
	::= { snIpxFwdFilterEntry 3 }

snIpxFwdFilterSrcNet	OBJECT-TYPE
	SYNTAX	NetNumber
	ACCESS  read-write
	STATUS  mandatory
	DESCRIPTION
		"Source Network Number."
	::= { snIpxFwdFilterEntry 4 }

snIpxFwdFilterSrcNode  OBJECT-TYPE
	SYNTAX	PhysAddress
	ACCESS  read-write
	STATUS  mandatory
	DESCRIPTION
		"Source Node Number."
	::= { snIpxFwdFilterEntry 5 }

snIpxFwdFilterDestNet	 OBJECT-TYPE
	SYNTAX	NetNumber
	ACCESS  read-write
	STATUS  mandatory
	DESCRIPTION
		"Destination Network Number."
	::= { snIpxFwdFilterEntry 6 }

snIpxFwdFilterDestNode	OBJECT-TYPE
	SYNTAX	PhysAddress
	ACCESS  read-write
	STATUS  mandatory
	DESCRIPTION
		"Destination Node Number."
	::= { snIpxFwdFilterEntry 7 }

snIpxFwdFilterRowStatus OBJECT-TYPE
	SYNTAX	 INTEGER {
	    invalid(1),
	    valid(2),
	    delete(3),
	    create(4),
	    modify(5)
	}
	ACCESS	 read-write
	STATUS	 mandatory
	DESCRIPTION
	"This object is used to create and
	 delete row in the table and control
	 if they are used. The values
	 that can be written are:
	 delete(3)...deletes the row
	 create(4)...creates a new row
	 modify(5)...modifies an exsisting row

	 If the row exists, then a SET with
	 value of create(4) returns error
	 'badValue'. Deleted rows go away
	 immediately. The following values
	 can be returned on reads:
	 noSuch(0)...no such row
	 invalid(1)...Setting it to 'invalid' has the effect of
		      rendering it inoperative..
	 valid(2)....the row exists and is valid"
	::= { snIpxFwdFilterEntry 8 }

-- ipx port counters table

snIpxPortCountersTable	       OBJECT-TYPE
	SYNTAX	SEQUENCE OF SnIpxPortCountersEntry
	ACCESS  not-accessible
	STATUS  mandatory
	DESCRIPTION
		"IPX port Counters table."
	::= { snIpxPortCounters 1 }

snIpxPortCountersEntry	       OBJECT-TYPE
	SYNTAX	SnIpxPortCountersEntry
	ACCESS  not-accessible
	STATUS  mandatory
	DESCRIPTION
		"An entry in the IPX Port Counters table."
	INDEX	{ snIpxPortCountersPort }
	::= { snIpxPortCountersTable 1 }

SnIpxPortCountersEntry ::= SEQUENCE {
	snIpxPortCountersPort
		PortIndex,
	snIpxPortCountersRcvPktsCnt
	    Counter,
	snIpxPortCountersFwdPktsCnt
	    Counter,
	snIpxPortCountersRcvFiltPktsCnt
	    Counter
	}


snIpxPortCountersPort	       OBJECT-TYPE
	SYNTAX  PortIndex
	ACCESS  read-only
	STATUS  mandatory
	DESCRIPTION
		"The port index for port Counters entry."
	::= { snIpxPortCountersEntry 1 }

snIpxPortCountersRcvPktsCnt 		OBJECT-TYPE
	SYNTAX	Counter
	ACCESS	read-only
	STATUS  mandatory
	DESCRIPTION
		"IPX incoming packets counter for the interface."
	::= { snIpxPortCountersEntry 2 }

snIpxPortCountersFwdPktsCnt 		OBJECT-TYPE
	SYNTAX	Counter
	ACCESS	read-only
	STATUS  mandatory
	DESCRIPTION
		"IPX forwarding packets counter for the interface."
	::= { snIpxPortCountersEntry 4 }

snIpxPortCountersRcvFiltPktsCnt		OBJECT-TYPE
	SYNTAX	Counter
	ACCESS	read-only
	STATUS  mandatory
	DESCRIPTION
		"IPX receiving filter packets counter for the interface."
	::= { snIpxPortCountersEntry 7 }

END

FOUNDRY-SN-SW-L4-SWITCH-GROUP-MIB DEFINITIONS ::= BEGIN


-- Foundry L4 Switch Group MIB Release 1.0.0
-- Revision 0 01/08/2000

-- Copyright 1996-98 Foundry Networks, Inc.
-- All rights reserved.
-- This Foundry Networks SNMP Management Information Base Specification
-- (Specification) embodies Foundry Networks' confidential and
-- proprietary intellectual property. Foundry Networks retains all
-- title and ownership in the Specification, including any
-- revisions.

-- This Specification is supplied "AS IS," and Foundry Networks makes
-- no warranty, either express or implied, as to the use,
-- operation, condition, or performance of the Specification.

-- SECTION 1: Top Level Definitions


-- Imports

IMPORTS
	IpAddress, Counter, TimeTicks
			FROM RFC1155-SMI
	 Counter64		FROM SNMPv2-SMI
   
	OBJECT-TYPE             
		FROM RFC-1212
	snL4
		FROM FOUNDRY-SN-ROOT-MIB;

	-- textual conventions
	-- maximum of ports are 32.  

	--  Row Creation/Deletion Values

	     L4RowSts ::= INTEGER { other(1),
							  valid(2),
							  delete(3),
							  create(4),
							  modify(5)
							}
	--  L4 Status Values

	    L4Status ::= INTEGER { disabled(0), enabled(1) }

	--  L4 Server Name
        L4ServerName ::= OCTET STRING (SIZE(1..32))

	--  L4 Flag Values
	    L4Flag ::= INTEGER { false(0), true(1) }

	--  L4 Delete Sate
	     L4DeleteState ::= INTEGER { done(0),
									 waitunbind(1),
									 waitdelete(2)
									}

	--  WebCacheSate
	     WebCacheState ::= INTEGER { disabled(0),
									 enabled(1),
									 failed(2),
									 testing(3),
									 suspect(4),
									 shutdown(5),
									 active(6)
									}

        PhysAddress ::= OCTET STRING
    -- This data type is used to model media addresses.  For many
    -- types of media, this will be in a binary representation.
    -- For example, an ethernet address would be represented as
    -- a string of 6 octets.

	  DisplayString ::=
	      OCTET STRING
	  -- This data type is used to model textual information taken
	  -- from the NVT ASCII character set.  By convention, objects
	  -- with this syntax are declared as having
	  --
	  --      SIZE (0..255)
    

snL4Gen						OBJECT IDENTIFIER	  ::= { snL4 1  }
snL4VirtualServer			OBJECT IDENTIFIER	  ::= { snL4 2  }
snL4RealServer				OBJECT IDENTIFIER	  ::= { snL4 3  }
snL4VirtualServerPort		OBJECT IDENTIFIER	  ::= { snL4 4  }
snL4RealServerPort			OBJECT IDENTIFIER	  ::= { snL4 5  }
snL4Bind					OBJECT IDENTIFIER	  ::= { snL4 6  }
snL4VirtualServerStatus		OBJECT IDENTIFIER	  ::= { snL4 7  }
snL4RealServerStatus		OBJECT IDENTIFIER	  ::= { snL4 8  }
snL4VirtualServerPortStatus	OBJECT IDENTIFIER	  ::= { snL4 9  }
snL4RealServerPortStatus	OBJECT IDENTIFIER	  ::= { snL4 10 }
snL4Policy					OBJECT IDENTIFIER	  ::= { snL4 11 }
snL4PolicyPortAccess		OBJECT IDENTIFIER	  ::= { snL4 12 }
snL4Trap					OBJECT IDENTIFIER	  ::= { snL4 13 }
snL4WebCache				OBJECT IDENTIFIER	  ::= { snL4 14 }
snL4WebCacheGroup			OBJECT IDENTIFIER	  ::= { snL4 15 }
snL4WebCacheTrafficStats	OBJECT IDENTIFIER	  ::= { snL4 16 }
snL4WebUncachedTrafficStats	OBJECT IDENTIFIER	  ::= { snL4 17 }
snL4WebCachePort			OBJECT IDENTIFIER	  ::= { snL4 18 }
snL4RealServerCfg			OBJECT IDENTIFIER	  ::= { snL4 19 }
snL4RealServerPortCfg		OBJECT IDENTIFIER	  ::= { snL4 20 }
snL4VirtualServerCfg		OBJECT IDENTIFIER	  ::= { snL4 21  }
snL4VirtualServerPortCfg	OBJECT IDENTIFIER	  ::= { snL4 22  }
snL4RealServerStatistic		OBJECT IDENTIFIER	  ::= { snL4 23 }
snL4RealServerPortStatistic	OBJECT IDENTIFIER	  ::= { snL4 24 }
snL4VirtualServerStatistic		OBJECT IDENTIFIER	  ::= { snL4 25 }
snL4VirtualServerPortStatistic	OBJECT IDENTIFIER	  ::= { snL4 26 }
snL4GslbSiteRemoteServerIrons	OBJECT IDENTIFIER 	  ::= { snL4 27 }
snL4History						OBJECT IDENTIFIER 	  ::= { snL4 28 }


-- L4 General MIBs
                
snL4MaxSessionLimit 		OBJECT-TYPE
	SYNTAX	INTEGER	(0..1000000)
	ACCESS  read-write
	STATUS  mandatory
	DESCRIPTION
		"numbers of maximum session (L4 cache) entries"
	::= { snL4Gen 1 }

snL4TcpSynLimit 		OBJECT-TYPE
	SYNTAX	INTEGER	 (1..65535)
	ACCESS  read-write
	STATUS  mandatory
	DESCRIPTION
		"Numbers of connection per second"
	::= { snL4Gen 2 }

--  Server load balancing
snL4slbGlobalSDAType	OBJECT-TYPE
	SYNTAX	 INTEGER {
	    leastconnection(1),
	    roundrobin(2),
	    weighted(3)
	}
	ACCESS  read-write
	STATUS  mandatory
	DESCRIPTION
		"Global Session Distribution Algorithm(SDA)"
	::= { snL4Gen 3 }

snL4slbTotalConnections 		OBJECT-TYPE
	SYNTAX	Counter
	ACCESS  read-only
	STATUS  mandatory
	DESCRIPTION
		"Total connections in this device"
	::= { snL4Gen 4 }

snL4slbLimitExceeds 		OBJECT-TYPE
	SYNTAX	INTEGER
	ACCESS  read-only
	STATUS  mandatory
	DESCRIPTION
		"exceeds snL4TCPSynLimit (numbers of connection per second)"
	::= { snL4Gen 5 }

-- Server load balancing traffic info

snL4slbForwardTraffic 		OBJECT-TYPE
	SYNTAX	Counter
	ACCESS  read-only
	STATUS  mandatory
	DESCRIPTION
		"Client->Server"
	::= { snL4Gen 6 }

snL4slbReverseTraffic 		OBJECT-TYPE
	SYNTAX	Counter
	ACCESS  read-only
	STATUS  mandatory
	DESCRIPTION
		"Server->Client"
	::= { snL4Gen 7 }

snL4slbDrops 		OBJECT-TYPE
	SYNTAX	INTEGER
	ACCESS  read-only
	STATUS  mandatory
	DESCRIPTION
		""
	::= { snL4Gen 8 }

snL4slbDangling 		OBJECT-TYPE
	SYNTAX	INTEGER
	ACCESS  read-only
	STATUS  mandatory
	DESCRIPTION
		""
	::= { snL4Gen 9 }

snL4slbDisableCount 		OBJECT-TYPE
	SYNTAX	INTEGER
	ACCESS  read-only
	STATUS  mandatory
	DESCRIPTION
		""
	::= { snL4Gen 10 }

snL4slbAged 		OBJECT-TYPE
	SYNTAX	INTEGER
	ACCESS  read-only
	STATUS  mandatory
	DESCRIPTION
		""
	::= { snL4Gen 11 }

snL4slbFinished 		OBJECT-TYPE
	SYNTAX	INTEGER
	ACCESS  read-only
	STATUS  mandatory
	DESCRIPTION
		"FIN_or_RST"
	::= { snL4Gen 12 }

--  Session

snL4FreeSessionCount 		OBJECT-TYPE
	SYNTAX	INTEGER
	ACCESS  read-only
	STATUS  mandatory
	DESCRIPTION
		"Maximum sessions - used sessions"
	::= { snL4Gen 13 }


--  Hot stand-by
snL4BackupInterface 		OBJECT-TYPE
	SYNTAX	INTEGER	  (0..26)
	ACCESS  read-write
	STATUS  mandatory
	DESCRIPTION
		"backup monitoring port"
	::= { snL4Gen 14 }

snL4BackupMacAddr 		OBJECT-TYPE
	SYNTAX	PhysAddress
	ACCESS  read-write
	STATUS  mandatory
	DESCRIPTION
		"Associated MAC address for backup monitoring port"
	::= { snL4Gen 15 }

snL4Active 		OBJECT-TYPE
	SYNTAX	L4Flag
	ACCESS  read-only
	STATUS  mandatory
	DESCRIPTION
		""
	::= { snL4Gen 16 }

snL4Redundancy 		OBJECT-TYPE
	SYNTAX	INTEGER
	ACCESS  read-only
	STATUS  mandatory
	DESCRIPTION
		""
	::= { snL4Gen 17 }

snL4Backup 		OBJECT-TYPE
	SYNTAX	L4Flag
	ACCESS  read-only
	STATUS  mandatory
	DESCRIPTION
		"true->StandBy,false->active"
	::= { snL4Gen 18 }

snL4BecomeActive 		OBJECT-TYPE
	SYNTAX	INTEGER
	ACCESS  read-only
	STATUS  mandatory
	DESCRIPTION
		"How many times this device become active"
	::= { snL4Gen 19 }

snL4BecomeStandBy 		OBJECT-TYPE
	SYNTAX	INTEGER
	ACCESS  read-only
	STATUS  mandatory
	DESCRIPTION
		"How many times this device become standby"
	::= { snL4Gen 20 }

snL4BackupState 		OBJECT-TYPE
	SYNTAX	 INTEGER {
		slbSyncComplete(0),
	    slbSyncReqMap(1),
	    slbSyncreqMac(2),
	    slbSyncreqServers(3),
	    slbSyncReqL4(4)
	}
	ACCESS  read-only
	STATUS  mandatory
	DESCRIPTION
		"Backup state"
	::= { snL4Gen 21 }

snL4NoPDUSent 		OBJECT-TYPE
	SYNTAX	INTEGER
	ACCESS  read-only
	STATUS  mandatory
	DESCRIPTION
		""
	::= { snL4Gen 22 }


snL4NoPDUCount 		OBJECT-TYPE
	SYNTAX	INTEGER
	ACCESS  read-only
	STATUS  mandatory
	DESCRIPTION
		""
	::= { snL4Gen 23 }


snL4NoPortMap 		OBJECT-TYPE
	SYNTAX	INTEGER
	ACCESS  read-only
	STATUS  mandatory
	DESCRIPTION
		""
	::= { snL4Gen 24 }

snL4unsuccessfulConn 	OBJECT-TYPE
	SYNTAX	INTEGER
	ACCESS  read-only
	STATUS  mandatory
	DESCRIPTION
		"Unsuccessfull connection"
	::= { snL4Gen 25 }

snL4PingInterval 	OBJECT-TYPE
	SYNTAX	INTEGER	 (1..10)
	ACCESS  read-write
	STATUS  mandatory
	DESCRIPTION
		"Ping retries interval"
    DEFVAL { 2 }
	::= { snL4Gen 26 }

snL4PingRetry 	OBJECT-TYPE
	SYNTAX	INTEGER	(2..10)
	ACCESS  read-write
	STATUS  mandatory
	DESCRIPTION
		"Ping retries attempts"
    DEFVAL { 4 }
	::= { snL4Gen 27 }

snL4TcpAge 	OBJECT-TYPE
	SYNTAX	INTEGER	(2..60)
	ACCESS  read-write
	STATUS  mandatory
	DESCRIPTION
		"TCP reset age"
    DEFVAL { 30 }
	::= { snL4Gen 28 }


snL4UdpAge 	OBJECT-TYPE
	SYNTAX	INTEGER	(2..60)
	ACCESS  read-write
	STATUS  mandatory
	DESCRIPTION
		"UDP reset age"
    DEFVAL { 5 }
	::= { snL4Gen 29 }


-- Enable/disable L4 traps

snL4EnableMaxSessionLimitReachedTrap        OBJECT-TYPE
	SYNTAX INTEGER { disabled(0), enabled(1) }
	ACCESS read-write
	STATUS mandatory
	DESCRIPTION
		"Enable/disable maximum number of connections reached trap."
	::= { snL4Gen 30 }

snL4EnableTcpSynLimitReachedTrap            OBJECT-TYPE
	SYNTAX INTEGER { disabled(0), enabled(1) }
	ACCESS read-write
	STATUS mandatory
	DESCRIPTION
		"Enable/disable the number of TCP SYN limits reached trap."
	::= { snL4Gen 31 }

snL4EnableRealServerUpTrap                  OBJECT-TYPE
	SYNTAX INTEGER { disabled(0), enabled(1) }
	ACCESS read-write
	STATUS mandatory
	DESCRIPTION
		"Enable/disable the real server up trap."
	::= { snL4Gen 32 }

snL4EnableRealServerDownTrap                OBJECT-TYPE
	SYNTAX INTEGER { disabled(0), enabled(1) }
	ACCESS read-write
	STATUS mandatory
	DESCRIPTION
		"Enable/disable the real server down trap."
	::= { snL4Gen 33 }

snL4EnableRealServerPortUpTrap              OBJECT-TYPE
	SYNTAX INTEGER { disabled(0), enabled(1) }
	ACCESS read-write
	STATUS mandatory
	DESCRIPTION
		"Enable/disable the real server TCP port up trap."
	::= { snL4Gen 34 }

snL4EnableRealServerPortDownTrap            OBJECT-TYPE
	SYNTAX INTEGER { disabled(0), enabled(1) }
	ACCESS read-write
	STATUS mandatory
	DESCRIPTION
		"Enable/disable the real server TCP port down trap."
	::= { snL4Gen 35 }

snL4EnableRealServerMaxConnLimitReachedTrap OBJECT-TYPE
	SYNTAX INTEGER { disabled(0), enabled(1) }
	ACCESS read-write
	STATUS mandatory
	DESCRIPTION
		"Enable/disable the real server maximum number of
		connections reached trap."
	::= { snL4Gen 36 }

snL4EnableBecomeStandbyTrap                 OBJECT-TYPE
	SYNTAX INTEGER { disabled(0), enabled(1) }
	ACCESS read-write
	STATUS mandatory
	DESCRIPTION
		"Enable/disable trap of the server load balancing
		switch changes state from active to standby."
	::= { snL4Gen 37 }

snL4EnableBecomeActiveTrap                  OBJECT-TYPE
	SYNTAX INTEGER { disabled(0), enabled(1) }
	ACCESS read-write
	STATUS mandatory
	DESCRIPTION
		"Enable/disable trap of the server load balancing
		switch changes state from standby to active."
	::= { snL4Gen 38 }

snL4slbRouterInterfacePortMask 	OBJECT-TYPE
	SYNTAX	INTEGER	
	ACCESS  read-write
	STATUS  deprecated
	DESCRIPTION
		"Router interface port mask.
		(It was obsoleted after release 07100, replaced by snL4slbRouterInterfacePortList)"
	::= { snL4Gen 39 }

------- Server Cache Group Global MIBs ----------
snL4MaxNumWebCacheGroup 		OBJECT-TYPE
	SYNTAX	INTEGER
	ACCESS  read-only
	STATUS  mandatory
	DESCRIPTION
		"The maximum number of server cache groups"
	::= { snL4Gen 40 }

snL4MaxNumWebCachePerGroup 		OBJECT-TYPE
	SYNTAX	INTEGER
	ACCESS  read-only
	STATUS  mandatory
	DESCRIPTION
		"The maximum number of WEB Cache servers in each of web cache group"
	::= { snL4Gen 41 }

snL4WebCacheStateful 		OBJECT-TYPE
	SYNTAX	L4Status
	ACCESS  read-write
	STATUS  mandatory
	DESCRIPTION
		"The WEB Cache servers cache-stateful"
	::= { snL4Gen 42 }

------- GSLB Group Global MIBs ----------
snL4EnableGslbHealthCheckIpUpTrap        OBJECT-TYPE
	SYNTAX INTEGER { disabled(0), enabled(1) }
	ACCESS read-write
	STATUS mandatory
	DESCRIPTION
		"Health check IP up."
	::= { snL4Gen 43 }

snL4EnableGslbHealthCheckIpDownTrap        OBJECT-TYPE
	SYNTAX INTEGER { disabled(0), enabled(1) }
	ACCESS read-write
	STATUS mandatory
	DESCRIPTION
		"Health check IP down."
	::= { snL4Gen 44 }


snL4EnableGslbHealthCheckIpPortUpTrap        OBJECT-TYPE
	SYNTAX INTEGER { disabled(0), enabled(1) }
	ACCESS read-write
	STATUS mandatory
	DESCRIPTION
		"Health check IP port up."
	::= { snL4Gen 45 }


snL4EnableGslbHealthCheckIpPortDownTrap        OBJECT-TYPE
	SYNTAX INTEGER { disabled(0), enabled(1) }
	ACCESS read-write
	STATUS mandatory
	DESCRIPTION
		"Health check IP port down."
	::= { snL4Gen 46 }


snL4EnableGslbRemoteGslbSiDownTrap        OBJECT-TYPE
	SYNTAX INTEGER { disabled(0), enabled(1) }
	ACCESS read-write
	STATUS mandatory
	DESCRIPTION
		"Connection to GSLB ServerIron is down."
	::= { snL4Gen 47 }


snL4EnableGslbRemoteGslbSiUpTrap        OBJECT-TYPE
	SYNTAX INTEGER { disabled(0), enabled(1) }
	ACCESS read-write
	STATUS mandatory
	DESCRIPTION
		"Connection to GSLB ServerIron is up."
	::= { snL4Gen 48 }


snL4EnableGslbRemoteSiDownTrap        OBJECT-TYPE
	SYNTAX INTEGER { disabled(0), enabled(1) }
	ACCESS read-write
	STATUS mandatory
	DESCRIPTION
		"GSLB connection to remote ServerIron is down."
	::= { snL4Gen 49 }


snL4EnableGslbRemoteSiUpTrap        OBJECT-TYPE
	SYNTAX INTEGER { disabled(0), enabled(1) }
	ACCESS read-write
	STATUS mandatory
	DESCRIPTION
		"GSLB connection to remote ServerIron is up."
	::= { snL4Gen 50 }

snL4slbRouterInterfacePortList 	OBJECT-TYPE
	SYNTAX	OCTET STRING
	ACCESS  read-write
	STATUS  mandatory
	DESCRIPTION
		"Router interface port list. Each port index is a 16-bit integer
		in big endian order. 8-bit is the slot number, the other 8-bit
		is the port number."
	::= { snL4Gen 51 }


-- Virtual Server table

snL4VirtualServerTable  OBJECT-TYPE
	SYNTAX	SEQUENCE OF SnL4VirtualServerEntry
	ACCESS  not-accessible
	STATUS  mandatory
	DESCRIPTION
		"Virtual Server table."
	::= { snL4VirtualServer 1 }

snL4VirtualServerEntry  OBJECT-TYPE
	SYNTAX	SnL4VirtualServerEntry
	ACCESS  not-accessible
	STATUS  mandatory
	DESCRIPTION
		"An entry in L4 Virtual Server table."
	INDEX	{ snL4VirtualServerIndex }
	::= { snL4VirtualServerTable 1 }

SnL4VirtualServerEntry ::= SEQUENCE {
	snL4VirtualServerIndex
		INTEGER,
    snL4VirtualServerName
        L4ServerName,
    snL4VirtualServerVirtualIP
		IpAddress,
    snL4VirtualServerAdminStatus
        L4Status,
	snL4VirtualServerSDAType
		INTEGER,
	snL4VirtualServerRowStatus
		L4RowSts,
    snL4VirtualServerDeleteState
        L4DeleteState
	}

snL4VirtualServerIndex  OBJECT-TYPE
	SYNTAX	INTEGER (1..64)
	ACCESS  read-only
	STATUS  mandatory
	DESCRIPTION
		"The table index for a Virtual Server  entry."
	::= { snL4VirtualServerEntry 1 }


snL4VirtualServerName  OBJECT-TYPE
	SYNTAX	L4ServerName
	ACCESS  read-write
	STATUS  mandatory
	DESCRIPTION
		"Virtual server name."
	::= { snL4VirtualServerEntry 2 }

snL4VirtualServerVirtualIP
	OBJECT-TYPE
	SYNTAX IpAddress
	ACCESS  read-write
	STATUS  mandatory
	DESCRIPTION
		"Virtual Server IP Address."
	::= { snL4VirtualServerEntry 3 }

snL4VirtualServerAdminStatus	OBJECT-TYPE
	SYNTAX	L4Status
	ACCESS  read-write
	STATUS  mandatory
	DESCRIPTION
		"Virtual Server status is ether disabled(0) or enabled(1)."
	::= { snL4VirtualServerEntry 4 }

snL4VirtualServerSDAType  OBJECT-TYPE
	SYNTAX	 INTEGER {
		default(0),
	    leastconnection(1),
	    roundrobin(2),
	    weighted(3)
	}
	ACCESS  read-write
	STATUS  mandatory
	DESCRIPTION
		"TCP/UDP Sessions Distribution Algorithms Type."
	::= { snL4VirtualServerEntry 5 }

 snL4VirtualServerRowStatus OBJECT-TYPE
	SYNTAX  L4RowSts
	ACCESS  read-write
	STATUS  mandatory
	DESCRIPTION
		"To create or delete a virtual server
		entry."
	::= {snL4VirtualServerEntry  6 }

snL4VirtualServerDeleteState	OBJECT-TYPE
	SYNTAX	L4DeleteState
	ACCESS  read-only
	STATUS  mandatory
	DESCRIPTION
		"Delete operation state." 
	::= { snL4VirtualServerEntry 7 }


-- Real Server table

snL4RealServerTable  OBJECT-TYPE
	SYNTAX	SEQUENCE OF SnL4RealServerEntry
	ACCESS  not-accessible
	STATUS  mandatory
	DESCRIPTION
		"Real Server table."
	::= { snL4RealServer 1 }

snL4RealServerEntry  OBJECT-TYPE
	SYNTAX	SnL4RealServerEntry
	ACCESS  not-accessible
	STATUS  mandatory
	DESCRIPTION
		"An entry in the Real Server table."
	INDEX	{ snL4RealServerIndex }
	::= { snL4RealServerTable 1 }

SnL4RealServerEntry ::= SEQUENCE {
	snL4RealServerIndex
		INTEGER,
    snL4RealServerName
        L4ServerName,
    snL4RealServerIP
		IpAddress,
    snL4RealServerAdminStatus
        L4Status,
	snL4RealServerMaxConnections
		INTEGER,
	snL4RealServerWeight
		INTEGER,
	snL4RealServerRowStatus
		L4RowSts,
    snL4RealServerDeleteState
        L4DeleteState
	}

snL4RealServerIndex  OBJECT-TYPE
	SYNTAX	INTEGER (1..256)
	ACCESS  read-only
	STATUS  mandatory
	DESCRIPTION
		"The table index for a Real Server entry."
	::= { snL4RealServerEntry 1 }
snL4RealServerName  OBJECT-TYPE
	SYNTAX	L4ServerName
	ACCESS  read-write
	STATUS  mandatory
	DESCRIPTION
		"Real server name."
	::= { snL4RealServerEntry 2 }

snL4RealServerIP
	OBJECT-TYPE
	SYNTAX IpAddress
	ACCESS  read-write
	STATUS  mandatory
	DESCRIPTION
		"Real Server IP Address."
	::= { snL4RealServerEntry 3 }

snL4RealServerAdminStatus	OBJECT-TYPE
	SYNTAX	L4Status
	ACCESS  read-write
	STATUS  mandatory
	DESCRIPTION
		"Real Server status is ether disabled(0) or enabled(1)."
	::= { snL4RealServerEntry 4 }

snL4RealServerMaxConnections 	OBJECT-TYPE
	SYNTAX	INTEGER	 (0..1000000)
	ACCESS  read-write
	STATUS  mandatory
	DESCRIPTION
		"Real Server Maximum Connection allowed."
	::= { snL4RealServerEntry 5 }

 snL4RealServerWeight	OBJECT-TYPE
	SYNTAX	INTEGER	  (0..65000)
	ACCESS  read-write
	STATUS  mandatory
	DESCRIPTION
		"Real Server weight"
	::= { snL4RealServerEntry 6 }

 snL4RealServerRowStatus OBJECT-TYPE
	SYNTAX  L4RowSts
	ACCESS  read-write
	STATUS  mandatory
	DESCRIPTION
		"To create or delete a real server entry."
	::= {snL4RealServerEntry  7 }

snL4RealServerDeleteState	OBJECT-TYPE
	SYNTAX	L4DeleteState
	ACCESS  read-only
	STATUS  mandatory
	DESCRIPTION
		"Delete operation state." 
	::= { snL4RealServerEntry 8 }



-- Virtual Server Port table

snL4VirtualServerPortTable	       OBJECT-TYPE
	SYNTAX	SEQUENCE OF SnL4VirtualServerPortEntry
	ACCESS  not-accessible
	STATUS  mandatory
	DESCRIPTION
		"Virtual Server Port table."
	::= { snL4VirtualServerPort 1 }

snL4VirtualServerPortEntry	       OBJECT-TYPE
	SYNTAX	SnL4VirtualServerPortEntry
	ACCESS  not-accessible
	STATUS  mandatory
	DESCRIPTION
		"An entry in the Virtual Server Port table."
	INDEX	{ snL4VirtualServerPortIndex }
	::= { snL4VirtualServerPortTable 1 }

SnL4VirtualServerPortEntry ::= SEQUENCE {
	snL4VirtualServerPortIndex
		INTEGER,
	snL4VirtualServerPortServerName
        L4ServerName,
	snL4VirtualServerPortPort
		INTEGER,
	snL4VirtualServerPortAdminStatus
		L4Status,
	snL4VirtualServerPortSticky
		INTEGER,
	snL4VirtualServerPortConcurrent
		INTEGER,
	snL4VirtualServerPortRowStatus
		L4RowSts,
    snL4VirtualServerPortDeleteState
        L4DeleteState
	}


snL4VirtualServerPortIndex	       OBJECT-TYPE
	SYNTAX	INTEGER (1..2048)
	ACCESS  read-only
	STATUS  mandatory
	DESCRIPTION
		"The index for Virtual Server Port entry."
	::= { snL4VirtualServerPortEntry 1 }


snL4VirtualServerPortServerName	       OBJECT-TYPE
	SYNTAX	L4ServerName
	ACCESS  read-write
	STATUS  mandatory
	DESCRIPTION
		""
	::= { snL4VirtualServerPortEntry 2 }

snL4VirtualServerPortPort       OBJECT-TYPE
	SYNTAX	INTEGER	  (0..65535)
	ACCESS  read-write
	STATUS  mandatory
	DESCRIPTION
		""
	::= { snL4VirtualServerPortEntry 3 }


snL4VirtualServerPortAdminStatus		       OBJECT-TYPE
	SYNTAX	L4Status
	ACCESS  read-write
	STATUS  mandatory
	DESCRIPTION
		""
	::= { snL4VirtualServerPortEntry 4 }


 snL4VirtualServerPortSticky       OBJECT-TYPE
	 SYNTAX  INTEGER {
			disabled(0),
			enabled(1)       
			}
	ACCESS  read-write
	STATUS  mandatory
	DESCRIPTION
		""
	::= { snL4VirtualServerPortEntry 5 }


 snL4VirtualServerPortConcurrent       OBJECT-TYPE
	 SYNTAX  INTEGER {
			disabled(0),
			enabled(1)       
			}
	ACCESS  read-write
	STATUS  mandatory
	DESCRIPTION
		""
	::= { snL4VirtualServerPortEntry 6 }


 snL4VirtualServerPortRowStatus	 	       OBJECT-TYPE
	SYNTAX L4RowSts	
	ACCESS  read-write
	STATUS  mandatory
	DESCRIPTION
		"To create or delete a virtual server  port entry."
	::= { snL4VirtualServerPortEntry 7 }

snL4VirtualServerPortDeleteState	OBJECT-TYPE
	SYNTAX	L4DeleteState
	ACCESS  read-only
	STATUS  mandatory
	DESCRIPTION
		"Delete operation state." 
	::= { snL4VirtualServerPortEntry 8 }




-- Real Server Port table

snL4RealServerPortTable	       OBJECT-TYPE
	SYNTAX	SEQUENCE OF SnL4RealServerPortEntry
	ACCESS  not-accessible
	STATUS  mandatory
	DESCRIPTION
		"Real Server Port table."
	::= { snL4RealServerPort 1 }

snL4RealServerPortEntry	       OBJECT-TYPE
	SYNTAX	SnL4RealServerPortEntry
	ACCESS  not-accessible
	STATUS  mandatory
	DESCRIPTION
		"An entry in the Real Server Port table."
	INDEX	{ snL4RealServerPortIndex }
	::= { snL4RealServerPortTable 1 }

SnL4RealServerPortEntry ::= SEQUENCE {
	snL4RealServerPortIndex
		INTEGER,
	snL4RealServerPortServerName
        L4ServerName,
	snL4RealServerPortPort
		INTEGER,
	snL4RealServerPortAdminStatus
		L4Status,
	snL4RealServerPortRowStatus
		L4RowSts,
    snL4RealServerPortDeleteState
        L4DeleteState
	}


snL4RealServerPortIndex	       OBJECT-TYPE
	SYNTAX	INTEGER (1..2048)
	ACCESS  read-only
	STATUS  mandatory
	DESCRIPTION
		"The index for Real Server Port entry."
	::= { snL4RealServerPortEntry 1 }
snL4RealServerPortServerName	       OBJECT-TYPE
	SYNTAX	L4ServerName
	ACCESS  read-write
	STATUS  mandatory
	DESCRIPTION
		""
	::= { snL4RealServerPortEntry 2 }

snL4RealServerPortPort       OBJECT-TYPE
	SYNTAX	INTEGER	 (0..65535)
	ACCESS  read-write
	STATUS  mandatory
	DESCRIPTION
		""
	::= { snL4RealServerPortEntry 3 }


snL4RealServerPortAdminStatus		       OBJECT-TYPE
	SYNTAX	L4Status
	ACCESS  read-write
	STATUS  mandatory
	DESCRIPTION
		""
	::= { snL4RealServerPortEntry 4 }

 snL4RealServerPortRowStatus	 	       OBJECT-TYPE
	SYNTAX L4RowSts	
	ACCESS  read-write
	STATUS  mandatory
	DESCRIPTION
		"To create or delete a Real server  port entry."
	::= { snL4RealServerPortEntry 5 }

snL4RealServerPortDeleteState	OBJECT-TYPE
	SYNTAX	L4DeleteState
	ACCESS  read-only
	STATUS  mandatory
	DESCRIPTION
		"Delete operation state." 
	::= { snL4RealServerPortEntry 6 }



-- Bind table

snL4BindTable	       OBJECT-TYPE
	SYNTAX	SEQUENCE OF SnL4BindEntry
	ACCESS  not-accessible
	STATUS  mandatory
	DESCRIPTION
		"Bind table."
	::= { snL4Bind 1 }

snL4BindEntry	       OBJECT-TYPE
	SYNTAX	SnL4BindEntry
	ACCESS  not-accessible
	STATUS  mandatory
	DESCRIPTION
		"An entry in the Bind table."
	INDEX	{ snL4BindIndex }
	::= { snL4BindTable 1 }

SnL4BindEntry ::= SEQUENCE {
	snL4BindIndex
		INTEGER,
	snL4BindVirtualServerName
        L4ServerName,
	snL4BindVirtualPortNumber
		INTEGER,
	snL4BindRealServerName
        L4ServerName,
	snL4BindRealPortNumber
		INTEGER,
	snL4BindRowStatus
		INTEGER
	}


snL4BindIndex	       OBJECT-TYPE
	SYNTAX	INTEGER (1..2048)
	ACCESS  read-only
	STATUS  mandatory
	DESCRIPTION
		"The index for Bind entry."
	::= { snL4BindEntry 1 }

snL4BindVirtualServerName 	       OBJECT-TYPE
	SYNTAX	L4ServerName
	ACCESS  read-write
	STATUS  mandatory
	DESCRIPTION
		""
	::= { snL4BindEntry 2 }

snL4BindVirtualPortNumber        OBJECT-TYPE
	SYNTAX	INTEGER	 (0..65535)
	ACCESS  read-write
	STATUS  mandatory
	DESCRIPTION
		""
	::= { snL4BindEntry 3 }


 snL4BindRealServerName	       OBJECT-TYPE
	SYNTAX	L4ServerName
	ACCESS  read-write
	STATUS  mandatory
	DESCRIPTION
		""
	::= { snL4BindEntry 4 }

snL4BindRealPortNumber       OBJECT-TYPE
	SYNTAX	INTEGER	 (0..65535)
	ACCESS  read-write
	STATUS  mandatory
	DESCRIPTION
		""
	::= { snL4BindEntry 5 }
snL4BindRowStatus  	 	       OBJECT-TYPE
	SYNTAX	 INTEGER {
			  other(1),
			  valid(2),
			 delete(3),
			 create(4)
	}
	ACCESS  read-write
	STATUS  mandatory
	DESCRIPTION
		"To create or delete bind entry."
	::= { snL4BindEntry 6 }





-- Virtual Server Status table

snL4VirtualServerStatusTable  OBJECT-TYPE
	SYNTAX	SEQUENCE OF SnL4VirtualServerStatusEntry
	ACCESS  not-accessible
	STATUS  mandatory
	DESCRIPTION
		"Virtual Server Status table."
	::= { snL4VirtualServerStatus 1 }

snL4VirtualServerStatusEntry  OBJECT-TYPE
	SYNTAX	SnL4VirtualServerStatusEntry
	ACCESS  not-accessible
	STATUS  mandatory
	DESCRIPTION
		"An entry in L4 Virtual Server Status table."
	INDEX	{ snL4VirtualServerStatusIndex }
	::= { snL4VirtualServerStatusTable 1 }

SnL4VirtualServerStatusEntry ::= SEQUENCE {
	snL4VirtualServerStatusIndex
		INTEGER,
    snL4VirtualServerStatusName
        L4ServerName,
	snL4VirtualServerStatusReceivePkts
		Counter,
	snL4VirtualServerStatusTransmitPkts
		Counter,
	snL4VirtualServerStatusTotalConnections
		Counter
	}

snL4VirtualServerStatusIndex  OBJECT-TYPE
	SYNTAX	INTEGER (1..64)
	ACCESS  read-only
	STATUS  mandatory
	DESCRIPTION
		"The table index for a Virtual Server  Status entry."
	::= { snL4VirtualServerStatusEntry 1 }


snL4VirtualServerStatusName  OBJECT-TYPE
	SYNTAX	L4ServerName
	ACCESS  read-only
	STATUS  mandatory
	DESCRIPTION
		"Virtual server name."
	::= { snL4VirtualServerStatusEntry 2 }


snL4VirtualServerStatusReceivePkts  OBJECT-TYPE
	SYNTAX	Counter
	ACCESS	read-only
	STATUS  mandatory
	DESCRIPTION
		"" 
	::= { snL4VirtualServerStatusEntry 3 }

snL4VirtualServerStatusTransmitPkts  OBJECT-TYPE
	SYNTAX	Counter
	ACCESS	read-only
	STATUS  mandatory
	DESCRIPTION
		"" 
	::= { snL4VirtualServerStatusEntry 4 }

snL4VirtualServerStatusTotalConnections  OBJECT-TYPE
	SYNTAX	Counter
	ACCESS	read-only
	STATUS  mandatory
	DESCRIPTION
		"" 
	::= { snL4VirtualServerStatusEntry 5 }


-- Real Server Status Table

snL4RealServerStatusTable  OBJECT-TYPE
	SYNTAX	SEQUENCE OF SnL4RealServerStatusEntry
	ACCESS  not-accessible
	STATUS  mandatory
	DESCRIPTION
		"Real Server Status table."
	::= { snL4RealServerStatus 1 }

snL4RealServerStatusEntry  OBJECT-TYPE
	SYNTAX	SnL4RealServerStatusEntry
	ACCESS  not-accessible
	STATUS  mandatory
	DESCRIPTION
		"An entry in the Real Server Status table."
	INDEX	{ snL4RealServerStatusIndex }
	::= { snL4RealServerStatusTable 1 }

SnL4RealServerStatusEntry ::= SEQUENCE {
	snL4RealServerStatusIndex
		INTEGER,
    snL4RealServerStatusName
        L4ServerName,
    snL4RealServerStatusRealIP
		IpAddress,
	snL4RealServerStatusReceivePkts
		Counter,
	snL4RealServerStatusTransmitPkts
		Counter,
	snL4RealServerStatusCurConnections
		INTEGER,
	snL4RealServerStatusTotalConnections
		Counter,
	snL4RealServerStatusAge
		INTEGER,
	snL4RealServerStatusState
		INTEGER,
	snL4RealServerStatusReassignments
		INTEGER,
	snL4RealServerStatusReassignmentLimit
		INTEGER,
	snL4RealServerStatusFailedPortExists
		INTEGER,
	snL4RealServerStatusFailTime
		INTEGER,
	snL4RealServerStatusPeakConnections
		INTEGER
	}

snL4RealServerStatusIndex  OBJECT-TYPE
	SYNTAX	INTEGER	 (1..256)
	ACCESS  read-only
	STATUS  mandatory
	DESCRIPTION
		"The table index for a Real Server Status entry."
	::= { snL4RealServerStatusEntry 1 }

snL4RealServerStatusName OBJECT-TYPE
	SYNTAX	L4ServerName
	ACCESS  read-only
	STATUS  mandatory
	DESCRIPTION
		""
	::= { snL4RealServerStatusEntry 2 }

snL4RealServerStatusRealIP OBJECT-TYPE
	SYNTAX	IpAddress
	ACCESS  read-only
	STATUS  mandatory
	DESCRIPTION
		""
	::= { snL4RealServerStatusEntry 3 }

snL4RealServerStatusReceivePkts	  OBJECT-TYPE
	SYNTAX	Counter
	ACCESS  read-only
	STATUS  mandatory
	DESCRIPTION
		""
	::= { snL4RealServerStatusEntry 4 }

snL4RealServerStatusTransmitPkts  OBJECT-TYPE
	SYNTAX	Counter
	ACCESS  read-only
	STATUS  mandatory
	DESCRIPTION
		""
	::= { snL4RealServerStatusEntry 5 }

snL4RealServerStatusCurConnections   OBJECT-TYPE
	SYNTAX	INTEGER
	ACCESS  read-only
	STATUS  mandatory
	DESCRIPTION
		""
	::= { snL4RealServerStatusEntry 6 }

snL4RealServerStatusTotalConnections   OBJECT-TYPE
	SYNTAX	Counter
	ACCESS  read-only
	STATUS  mandatory
	DESCRIPTION
		""
	::= { snL4RealServerStatusEntry 7 }

snL4RealServerStatusAge  OBJECT-TYPE
	SYNTAX	INTEGER
	ACCESS  read-only
	STATUS  mandatory
	DESCRIPTION
		""
	::= { snL4RealServerStatusEntry 8 }

snL4RealServerStatusState  OBJECT-TYPE
	SYNTAX	INTEGER	{
	serverdisabled(0),
	serverenabled(1),
	serverfailed(2),
	servertesting(3),
	serversuspect(4),
	servershutdown(5),
	serveractive(6)
	}
	ACCESS  read-only
	STATUS  mandatory
	DESCRIPTION
		""
	::= { snL4RealServerStatusEntry 9 }

snL4RealServerStatusReassignments  OBJECT-TYPE
	SYNTAX	INTEGER
	ACCESS  read-only
	STATUS  mandatory
	DESCRIPTION
		""
	::= { snL4RealServerStatusEntry 10 }

snL4RealServerStatusReassignmentLimit  OBJECT-TYPE
	SYNTAX	INTEGER
	ACCESS  read-only
	STATUS  mandatory
	DESCRIPTION
		""
	::= { snL4RealServerStatusEntry 11 }

snL4RealServerStatusFailedPortExists  OBJECT-TYPE
	SYNTAX	INTEGER
	ACCESS  read-only
	STATUS  mandatory
	DESCRIPTION
		""
	::= { snL4RealServerStatusEntry 12 }

snL4RealServerStatusFailTime  OBJECT-TYPE
	SYNTAX	INTEGER
	ACCESS  read-only
	STATUS  mandatory
	DESCRIPTION
		""
	::= { snL4RealServerStatusEntry 13 }


snL4RealServerStatusPeakConnections   OBJECT-TYPE
	SYNTAX	INTEGER
	ACCESS  read-only
	STATUS  mandatory
	DESCRIPTION
		""
	::= { snL4RealServerStatusEntry 14 }




-- Virtual Server Port Status table

snL4VirtualServerPortStatusTable	       OBJECT-TYPE
	SYNTAX	SEQUENCE OF SnL4VirtualServerPortStatusEntry
	ACCESS  not-accessible
	STATUS  mandatory
	DESCRIPTION
		"Virtual Server Port Status table."
	::= { snL4VirtualServerPortStatus 1 }

snL4VirtualServerPortStatusEntry	       OBJECT-TYPE
	SYNTAX	SnL4VirtualServerPortStatusEntry
	ACCESS  not-accessible
	STATUS  mandatory
	DESCRIPTION
		"An entry in the Virtual Server Port Status table."
	INDEX	{ snL4VirtualServerPortStatusIndex }
	::= { snL4VirtualServerPortStatusTable 1 }

SnL4VirtualServerPortStatusEntry ::= SEQUENCE {
	snL4VirtualServerPortStatusIndex
		INTEGER,
	snL4VirtualServerPortStatusPort
		INTEGER,
	snL4VirtualServerPortStatusServerName
        L4ServerName,
	snL4VirtualServerPortStatusCurrentConnection
		INTEGER,
	snL4VirtualServerPortStatusTotalConnection
		Counter,
	snL4VirtualServerPortStatusPeakConnection
		INTEGER
	}

snL4VirtualServerPortStatusIndex	       OBJECT-TYPE
	SYNTAX	INTEGER
	ACCESS  read-only
	STATUS  mandatory
	DESCRIPTION
		"The index for Virtual Server Port Status entry."
	::= { snL4VirtualServerPortStatusEntry 1 }

snL4VirtualServerPortStatusPort   OBJECT-TYPE
	SYNTAX	INTEGER	 (1..2048)
	ACCESS  read-only
	STATUS  mandatory
	DESCRIPTION
		""
	::= { snL4VirtualServerPortStatusEntry 2 }

 snL4VirtualServerPortStatusServerName 	       OBJECT-TYPE
	SYNTAX	L4ServerName
	ACCESS  read-only
	STATUS  mandatory
	DESCRIPTION
		""
	::= { snL4VirtualServerPortStatusEntry 3 }

 snL4VirtualServerPortStatusCurrentConnection 	       OBJECT-TYPE
	SYNTAX	INTEGER
	ACCESS  read-only
	STATUS  mandatory
	DESCRIPTION
		""
	::= { snL4VirtualServerPortStatusEntry 4 }

 snL4VirtualServerPortStatusTotalConnection		       OBJECT-TYPE
	SYNTAX	Counter
	ACCESS  read-only
	STATUS  mandatory
	DESCRIPTION
		""
	::= { snL4VirtualServerPortStatusEntry 5 }

 snL4VirtualServerPortStatusPeakConnection 	       OBJECT-TYPE
	SYNTAX	INTEGER
	ACCESS  read-only
	STATUS  mandatory
	DESCRIPTION
		""
	::= { snL4VirtualServerPortStatusEntry 6 }

-- Real Server Port Status table

snL4RealServerPortStatusTable	       OBJECT-TYPE
	SYNTAX	SEQUENCE OF SnL4RealServerPortStatusEntry
	ACCESS  not-accessible
	STATUS  mandatory
	DESCRIPTION
		"Real Server Port Status table."
	::= { snL4RealServerPortStatus 1 }

snL4RealServerPortStatusEntry	       OBJECT-TYPE
	SYNTAX	SnL4RealServerPortStatusEntry
	ACCESS  not-accessible
	STATUS  mandatory
	DESCRIPTION
		"An entry in the Real Server Port Status table."
	INDEX	{ snL4RealServerPortStatusIndex }
	::= { snL4RealServerPortStatusTable 1 }

SnL4RealServerPortStatusEntry ::= SEQUENCE {
	snL4RealServerPortStatusIndex
		INTEGER,
	snL4RealServerPortStatusPort
		INTEGER,
	snL4RealServerPortStatusServerName
        L4ServerName,
	snL4RealServerPortStatusReassignCount
		INTEGER,
	snL4RealServerPortStatusState
		INTEGER,
	snL4RealServerPortStatusFailTime
		INTEGER,
	snL4RealServerPortStatusCurrentConnection
		INTEGER,
	snL4RealServerPortStatusTotalConnection
		Counter,
	snL4RealServerPortStatusRxPkts
		Counter,
	snL4RealServerPortStatusTxPkts
		Counter,
	snL4RealServerPortStatusRxBytes
		Counter,
	snL4RealServerPortStatusTxBytes
		Counter,
	snL4RealServerPortStatusPeakConnection
		INTEGER
	}


snL4RealServerPortStatusIndex	       OBJECT-TYPE
	SYNTAX	INTEGER	  (1..2048)
	ACCESS  read-only
	STATUS  mandatory
	DESCRIPTION
		"The index for Real Server Port Status entry."
	::= { snL4RealServerPortStatusEntry 1 }

snL4RealServerPortStatusPort	       OBJECT-TYPE
	SYNTAX	INTEGER
	ACCESS  read-only
	STATUS  mandatory
	DESCRIPTION
		""
	::= { snL4RealServerPortStatusEntry 2 }

snL4RealServerPortStatusServerName	       OBJECT-TYPE
	SYNTAX	L4ServerName
	ACCESS  read-only
	STATUS  mandatory
	DESCRIPTION
		""
	::= { snL4RealServerPortStatusEntry 3 }

snL4RealServerPortStatusReassignCount	       OBJECT-TYPE
	SYNTAX	INTEGER
	ACCESS  read-only
	STATUS  mandatory
	DESCRIPTION
		""
	::= { snL4RealServerPortStatusEntry 4 }

 snL4RealServerPortStatusState	       OBJECT-TYPE
	SYNTAX	INTEGER	{
		disabled(0),
		enabled(1),
		failed(2),
		testing(3),
		suspect(4),
	    shutdown(5),
		active(6),
		unbound(7),
		awaitUnbind(8),
		awaitDelete(9)
	}
	ACCESS  read-only
	STATUS  mandatory
	DESCRIPTION
		"Real server port state"
	::= { snL4RealServerPortStatusEntry 5 }

snL4RealServerPortStatusFailTime 	       OBJECT-TYPE
	SYNTAX	INTEGER
	ACCESS  read-only
	STATUS  mandatory
	DESCRIPTION
		"Only useful, if real server port state is failed.
		 Indicating how seconds has been elapsed from the last retry."
 	::= { snL4RealServerPortStatusEntry 6 }

snL4RealServerPortStatusCurrentConnection	       OBJECT-TYPE
	SYNTAX	INTEGER
	ACCESS  read-only
	STATUS  mandatory
	DESCRIPTION
		"Real server port current connection"
	::= { snL4RealServerPortStatusEntry 7 }

snL4RealServerPortStatusTotalConnection	       OBJECT-TYPE
	SYNTAX	Counter
	ACCESS  read-only
	STATUS  mandatory
	DESCRIPTION
		"Real server port total connection"
	::= { snL4RealServerPortStatusEntry 8 }

snL4RealServerPortStatusRxPkts	       OBJECT-TYPE
	SYNTAX	Counter
	ACCESS  read-only
	STATUS  mandatory
	DESCRIPTION
		"Real server port receive packets."
	::= { snL4RealServerPortStatusEntry 9 }


snL4RealServerPortStatusTxPkts	       OBJECT-TYPE
	SYNTAX	Counter
	ACCESS  read-only
	STATUS  mandatory
	DESCRIPTION
		"Real server port transmit packets."
	::= { snL4RealServerPortStatusEntry 10 }


snL4RealServerPortStatusRxBytes	       OBJECT-TYPE
	SYNTAX	Counter
	ACCESS  read-only
	STATUS  mandatory
	DESCRIPTION
		"Real server port receive bytes."
	::= { snL4RealServerPortStatusEntry 11 }

snL4RealServerPortStatusTxBytes	       OBJECT-TYPE
	SYNTAX	Counter
	ACCESS  read-only
	STATUS  mandatory
	DESCRIPTION
		"Real server port transmit bytes."
	::= { snL4RealServerPortStatusEntry 12 }


snL4RealServerPortStatusPeakConnection	       OBJECT-TYPE
	SYNTAX	INTEGER
	ACCESS  read-only
	STATUS  mandatory
	DESCRIPTION
		"peak connection for real server port."
	::= { snL4RealServerPortStatusEntry 13 }




-- L4 policy table

snL4PolicyTable	  OBJECT-TYPE
	SYNTAX	SEQUENCE OF SnL4PolicyEntry
	ACCESS  not-accessible
	STATUS  mandatory
	DESCRIPTION
		"L4 policy table."
	::= {snL4Policy  1 }

snL4PolicyEntry	  OBJECT-TYPE
	SYNTAX	SnL4PolicyEntry
	ACCESS  not-accessible
	STATUS  mandatory
	DESCRIPTION
		"An entry of the L4 policy table."
	INDEX	{ snL4PolicyId }
	::= { snL4PolicyTable 1 }

SnL4PolicyEntry ::= SEQUENCE {
	snL4PolicyId
		INTEGER,
	snL4PolicyPriority
		INTEGER,
	snL4PolicyScope
		INTEGER,
	snL4PolicyProtocol
		INTEGER,
	snL4PolicyPort
		INTEGER,
	snL4PolicyRowStatus
		INTEGER
	}

snL4PolicyId         OBJECT-TYPE
	SYNTAX	INTEGER (1..64)
	ACCESS  read-only
	STATUS  mandatory
	DESCRIPTION
		"The  ID to identify a  entry."
	::= { snL4PolicyEntry 1 }

snL4PolicyPriority	   OBJECT-TYPE
	SYNTAX  INTEGER {
		level0(0),
		level1(1),
		level2(2),
		level3(3),
		level4(4),
		level5(5),
		level6(6),
		level7(7)
		}
	ACCESS  read-write
	STATUS  mandatory
	DESCRIPTION
		"The Stand alone stackable switch L4 Policy Priority values are:
		 normal(0)   		 -- normal prority
		 high(1) 	 		 -- high prority
		 cache(2) 	 		 -- prority for cache
		 transparent(3) 	 -- prority for transparent
		 The BigIron switch L4 Priority values are:
		level0(0), level1(1), level2(2), level3(3),
		level4(4), level5(5), level6(6), level7(7) "
	::= { snL4PolicyEntry 2 }

snL4PolicyScope	   OBJECT-TYPE
	SYNTAX	INTEGER { global(0), local(1) }
	ACCESS  read-write
	STATUS  mandatory
	DESCRIPTION
		" Scope of the  local or global.
		  Global  automatic apply to all port.
		  Local  apply to a port."
	::= { snL4PolicyEntry 3 }

snL4PolicyProtocol     OBJECT-TYPE
	SYNTAX	INTEGER { udp(0), tcp(1) }

	ACCESS  read-write
	STATUS  mandatory
	DESCRIPTION
		""
	::= { snL4PolicyEntry 4 }

snL4PolicyPort OBJECT-TYPE
	SYNTAX	INTEGER	 (0..65535)
	ACCESS  read-write
	STATUS  mandatory
	DESCRIPTION ""
	::= { snL4PolicyEntry 5 }

snL4PolicyRowStatus  OBJECT-TYPE
	SYNTAX	INTEGER {
	    invalid(1),
	    valid(2),
	    delete(3),
	    create(4),
	    modify(5)
	}
	ACCESS	 read-write
	STATUS	 mandatory
	DESCRIPTION
		"This object is used to create and
		delete row in the table and control
		if they are used. The values
		that can be written are:
		delete(3)...deletes the row
		create(4)...creates a new row
		modify(5)...modifies an exsisting row

		If the row exists, then a SET with
		value of create(4) returns error
		'badValue'. Deleted rows go away
		immediately. The following values
		can be returned on reads:
		invalid(1)...Setting it to 'invalid' has the effect of
		             rendering it inoperative.
		valid(2).....the row exists and is valid"
	::= { snL4PolicyEntry 6 }

-- L4 policy port access table

snL4PolicyPortAccessTable	     OBJECT-TYPE
	SYNTAX	SEQUENCE OF SnL4PolicyPortAccessEntry
	ACCESS  not-accessible
	STATUS  mandatory
	DESCRIPTION
		"ip interface L4 policy access table."
	::= {snL4PolicyPortAccess  1}

snL4PolicyPortAccessEntry	     OBJECT-TYPE
	SYNTAX	SnL4PolicyPortAccessEntry
	ACCESS  not-accessible
	STATUS  mandatory
	DESCRIPTION
		"An entry of the ip interface L4 policy access  table."
	INDEX	{ snL4PolicyPortAccessPort }
	::= { snL4PolicyPortAccessTable 1 }

SnL4PolicyPortAccessEntry ::= SEQUENCE {
	snL4PolicyPortAccessPort
		INTEGER,
	snL4PolicyPortAccessList
		OCTET STRING,
	snL4PolicyPortAccessRowStatus
		INTEGER
	}

snL4PolicyPortAccessPort	     OBJECT-TYPE
	SYNTAX	INTEGER	
	ACCESS  read-only
	STATUS  mandatory
	DESCRIPTION
		"The ip interface to which the L4 policy  applies."
	::= { snL4PolicyPortAccessEntry 1 }

snL4PolicyPortAccessList  OBJECT-TYPE
	SYNTAX	OCTET STRING (SIZE(1..64))
	ACCESS  read-write
	STATUS  mandatory
	DESCRIPTION
		"An ip L4 policy  list, of which each octet contains
		a  ID number that forms a group of s. A
		valid entry in the snL4PolicyTable with the
		corresponding  ID number (i.e. snL4PolicyId)
		must have been created before a  list is initialized."
	::= { snL4PolicyPortAccessEntry 2 }

snL4PolicyPortAccessRowStatus   OBJECT-TYPE
	SYNTAX	 INTEGER {
	    invalid(1),
	    valid(2),
	    delete(3),
	    create(4),
	    modify(5)
	}
	ACCESS	 read-write
	STATUS	 mandatory
	DESCRIPTION
		"This object is used to create and
		delete row in the table and control
		if they are used. The values
		that can be written are:
		delete(3)...deletes the row
		create(4)...creates a new row
		modify(5)...modifies an exsisting row

		If the row exists, then a SET with
		value of create(4) returns error
		'badValue'. Deleted rows go away
		immediately. The following values
		can be returned on reads:
		invalid(1)...Setting it to 'invalid' has the effect of
		             rendering it inoperative.
		valid(2).....the row exists and is valid"
	::= { snL4PolicyPortAccessEntry 3 }

-- L4 trap variable binding objects

snL4TrapRealServerIP             OBJECT-TYPE
	SYNTAX IpAddress
	ACCESS not-accessible
	STATUS mandatory
	DESCRIPTION
		"Real server IP address."
	::= { snL4Trap 1 }

snL4TrapRealServerName           OBJECT-TYPE
	SYNTAX L4ServerName
	ACCESS not-accessible
	STATUS mandatory
	DESCRIPTION
		"Real server name."
	::= { snL4Trap 2 }

snL4TrapRealServerPort           OBJECT-TYPE
	SYNTAX INTEGER
	ACCESS not-accessible
	STATUS mandatory
	DESCRIPTION
		"Transport protocol port number of the real server."
	::= { snL4Trap 3 }

snL4TrapRealServerCurConnections OBJECT-TYPE
	SYNTAX INTEGER
	ACCESS not-accessible
	STATUS mandatory
	DESCRIPTION
		"Real Server current connections."
	::= { snL4Trap 4 }

snL4TrapLinkName OBJECT-TYPE
	SYNTAX L4ServerName
	ACCESS not-accessible
	STATUS mandatory
	DESCRIPTION
		"Link name."
	::= { snL4Trap 5 }

snL4LinkVirtualInterface OBJECT-TYPE
	SYNTAX INTEGER
	ACCESS not-accessible
	STATUS mandatory
	DESCRIPTION
		"Link virtual interface."
	::= { snL4Trap 6 }

-- Web Cache table

snL4WebCacheTable  OBJECT-TYPE
	SYNTAX	SEQUENCE OF SnL4WebCacheEntry
	ACCESS  not-accessible
	STATUS  mandatory
	DESCRIPTION
		"Real Server table."
	::= { snL4WebCache 1 }

snL4WebCacheEntry  OBJECT-TYPE
	SYNTAX	SnL4WebCacheEntry
	ACCESS  not-accessible
	STATUS  mandatory
	DESCRIPTION
		"An entry in the Real Server table."
	INDEX	{ snL4WebCacheIP }
	::= { snL4WebCacheTable 1 }

SnL4WebCacheEntry ::= SEQUENCE {
    snL4WebCacheIP
		IpAddress,
    snL4WebCacheName
        L4ServerName,
    snL4WebCacheAdminStatus
        L4Status,
	snL4WebCacheMaxConnections
		INTEGER,
	snL4WebCacheWeight
		INTEGER,
	snL4WebCacheRowStatus
		L4RowSts,
    snL4WebCacheDeleteState
        L4DeleteState
	}

snL4WebCacheIP
	OBJECT-TYPE
	SYNTAX IpAddress
	ACCESS  read-only
	STATUS  mandatory
	DESCRIPTION
		"Real Server IP Address."
	::= { snL4WebCacheEntry 1 }

snL4WebCacheName  OBJECT-TYPE
	SYNTAX	L4ServerName
	ACCESS  read-write
	STATUS  mandatory
	DESCRIPTION
		"Real server name."
	::= { snL4WebCacheEntry 2 }

snL4WebCacheAdminStatus	OBJECT-TYPE
	SYNTAX	L4Status
	ACCESS  read-write
	STATUS  mandatory
	DESCRIPTION
		"Real Server status is ether disabled(0) or enabled(1)."
	::= { snL4WebCacheEntry 3 }

snL4WebCacheMaxConnections 	OBJECT-TYPE
	SYNTAX	INTEGER	 (0..1000000)
	ACCESS  read-write
	STATUS  mandatory
	DESCRIPTION
		"Real Server Maximum Connection allowed."
	::= { snL4WebCacheEntry 4 }

 snL4WebCacheWeight	OBJECT-TYPE
	SYNTAX	INTEGER	  (1..20)
	ACCESS  read-write
	STATUS  mandatory
	DESCRIPTION
		"Real Server weight"
	::= { snL4WebCacheEntry 5 }

 snL4WebCacheRowStatus OBJECT-TYPE
	SYNTAX  L4RowSts
	ACCESS  read-write
	STATUS  mandatory
	DESCRIPTION
		"To create or delete a real server entry."
	::= {snL4WebCacheEntry  6 }

snL4WebCacheDeleteState	OBJECT-TYPE
	SYNTAX	L4DeleteState
	ACCESS  read-only
	STATUS  mandatory
	DESCRIPTION
		"Delete operation state." 
	::= { snL4WebCacheEntry 7 }


-- Web Cache Group table


snL4WebCacheGroupTable  OBJECT-TYPE
	SYNTAX	SEQUENCE OF SnL4WebCacheGroupEntry
	ACCESS  not-accessible
	STATUS  mandatory
	DESCRIPTION
		"Web Cache Group table."
	::= { snL4WebCacheGroup 1 }

snL4WebCacheGroupEntry  OBJECT-TYPE
	SYNTAX	SnL4WebCacheGroupEntry
	ACCESS  not-accessible
	STATUS  mandatory
	DESCRIPTION
		"An entry in the  Web Cache Group table."
	INDEX	{ snL4WebCacheGroupId }
	::= { snL4WebCacheGroupTable 1 }

SnL4WebCacheGroupEntry ::= SEQUENCE {
	snL4WebCacheGroupId
		INTEGER,
    snL4WebCacheGroupName
        L4ServerName,
    snL4WebCacheGroupWebCacheIpList
		OCTET STRING,
    snL4WebCacheGroupDestMask
		IpAddress,
    snL4WebCacheGroupSrcMask
		IpAddress,
	snL4WebCacheGroupAdminStatus
		INTEGER,
	snL4WebCacheGroupRowStatus
		L4RowSts
	}

snL4WebCacheGroupId  OBJECT-TYPE
	SYNTAX	INTEGER 
	ACCESS  read-only
	STATUS  mandatory
	DESCRIPTION
		"The identification for a Web Cache Group entry.
		 The limit is from 1 to snL4MaxNumWebCacheGroup."
	::= { snL4WebCacheGroupEntry 1 }

snL4WebCacheGroupName  OBJECT-TYPE
	SYNTAX	L4ServerName
	ACCESS  read-write
	STATUS  mandatory
	DESCRIPTION
		"Web Cache Group name."
	::= { snL4WebCacheGroupEntry 2 }

snL4WebCacheGroupWebCacheIpList
	OBJECT-TYPE
	SYNTAX	OCTET STRING
	ACCESS  read-write
	STATUS  mandatory
	DESCRIPTION
		"A list of the Server Cache Group Real Server IP Address.
		 The number of IP Address is from 1 (4 OCTETs) to the 
		 snL4MaxNumServersPerWebCacheGroup, maximum number of 
		 server IP Address allowed in the list."
	::= { snL4WebCacheGroupEntry 3 }

snL4WebCacheGroupDestMask 	OBJECT-TYPE
	SYNTAX  IpAddress
	ACCESS  read-write
	STATUS  mandatory
	DESCRIPTION
		"Cache Server Group Destination Mask."
	::= { snL4WebCacheGroupEntry 4 }

snL4WebCacheGroupSrcMask 	OBJECT-TYPE
	SYNTAX  IpAddress
	ACCESS  read-write
	STATUS  mandatory
	DESCRIPTION
		"Cache Server Group Source Mask."
	::= { snL4WebCacheGroupEntry 5 }

snL4WebCacheGroupAdminStatus OBJECT-TYPE
	SYNTAX  INTEGER {
		disabled(0),             
		enabled(1)
		}
	ACCESS  read-write
	STATUS  mandatory
	DESCRIPTION
		"The WEB Cache Group is set either
		 enabled(1)...........activated.
		 disabled(0)..........disabled."  
	::= { snL4WebCacheGroupEntry 6 }

 snL4WebCacheGroupRowStatus OBJECT-TYPE
	SYNTAX  L4RowSts
	ACCESS  read-write
	STATUS  mandatory
	DESCRIPTION
		"To create or delete a Web Cache Group entry."
	::= { snL4WebCacheGroupEntry 7 }


-- Web Cache Traffic Statistics Table 

snL4WebCacheTrafficStatsTable  OBJECT-TYPE
	SYNTAX	SEQUENCE OF SnL4WebCacheTrafficStatsEntry
	ACCESS  not-accessible
	STATUS  mandatory
	DESCRIPTION
		"Web Cache Traffic Statistics table."
	::= { snL4WebCacheTrafficStats 1 }

snL4WebCacheTrafficStatsEntry  OBJECT-TYPE
	SYNTAX	SnL4WebCacheTrafficStatsEntry
	ACCESS  not-accessible
	STATUS  mandatory
	DESCRIPTION
		"An entry in the Web Cache Traffic Statistics table."
	INDEX	{ snL4WebCacheTrafficIp , snL4WebCacheTrafficPort}
	::= { snL4WebCacheTrafficStatsTable 1 }

SnL4WebCacheTrafficStatsEntry ::= SEQUENCE {
    snL4WebCacheTrafficIp
		IpAddress,
    snL4WebCacheTrafficPort
		INTEGER,
    snL4WebCacheCurrConnections
		INTEGER,
    snL4WebCacheTotalConnections
		INTEGER,
	snL4WebCacheTxPkts
		Counter,
	snL4WebCacheRxPkts
		Counter,
	snL4WebCacheTxOctets
		Counter,
	snL4WebCacheRxOctets
		Counter,
    snL4WebCachePortState
		WebCacheState
	}

snL4WebCacheTrafficIp 	OBJECT-TYPE
	SYNTAX  IpAddress
	ACCESS  read-only
	STATUS  mandatory
	DESCRIPTION
		"Cache Server IP Address."
	::= { snL4WebCacheTrafficStatsEntry 1 }

snL4WebCacheTrafficPort 		OBJECT-TYPE
    SYNTAX  INTEGER (0..65535)
	ACCESS  read-only
	STATUS  mandatory
	DESCRIPTION
		"The WEB Cache port is one of the protocol port such as UDP, TCP etc."
	::= { snL4WebCacheTrafficStatsEntry 2 }

snL4WebCacheCurrConnections 		OBJECT-TYPE
	SYNTAX	INTEGER
	ACCESS  read-only
	STATUS  mandatory
	DESCRIPTION
		"Number of the current connections in WEB Cache group."
	::= { snL4WebCacheTrafficStatsEntry 3 }

snL4WebCacheTotalConnections 		OBJECT-TYPE
	SYNTAX	INTEGER
	ACCESS  read-only
	STATUS  mandatory
	DESCRIPTION
		"The total connections in WEB Cache group."
	::= { snL4WebCacheTrafficStatsEntry 4 }

snL4WebCacheTxPkts 		OBJECT-TYPE
	SYNTAX	Counter
	ACCESS  read-only
	STATUS  mandatory
	DESCRIPTION
		"Number of the Packets sending from Client/Web-Server to Cache Server"
	::= { snL4WebCacheTrafficStatsEntry 5 }

snL4WebCacheRxPkts 		OBJECT-TYPE
	SYNTAX	Counter
	ACCESS  read-only
	STATUS  mandatory
	DESCRIPTION
		"Number of the Packets sending from Cache Server to Client/Web-Server"
	::= { snL4WebCacheTrafficStatsEntry 6 }

snL4WebCacheTxOctets 		OBJECT-TYPE
	SYNTAX	Counter
	ACCESS  read-only
	STATUS  mandatory
	DESCRIPTION
		"Number of the Octets sending from Client/Web-Server to Cache Server"
	::= { snL4WebCacheTrafficStatsEntry 7 }

snL4WebCacheRxOctets 		OBJECT-TYPE
	SYNTAX	Counter
	ACCESS  read-only
	STATUS  mandatory
	DESCRIPTION
		"Number of the Octets sending from Cache Server to Client/Web-Server"
	::= { snL4WebCacheTrafficStatsEntry 8 }

snL4WebCachePortState	OBJECT-TYPE
	SYNTAX	WebCacheState
	ACCESS  read-only
	STATUS  mandatory
	DESCRIPTION
		"Web Cache Port state." 
	::= { snL4WebCacheTrafficStatsEntry 9 }

-- Web Uncached Traffic Statistics Table 

snL4WebUncachedTrafficStatsTable  OBJECT-TYPE
	SYNTAX	SEQUENCE OF SnL4WebUncachedTrafficStatsEntry
	ACCESS  not-accessible
	STATUS  mandatory
	DESCRIPTION
		"Web Uncached Traffic Statistics table."
	::= { snL4WebUncachedTrafficStats 1 }

snL4WebUncachedTrafficStatsEntry  OBJECT-TYPE
	SYNTAX	SnL4WebUncachedTrafficStatsEntry
	ACCESS  not-accessible
	STATUS  mandatory
	DESCRIPTION
		"An entry in the Web Uncached Traffic Statistics table."
	INDEX	{ snL4WebServerPort, snL4WebClientPort }
	::= { snL4WebUncachedTrafficStatsTable 1 }

SnL4WebUncachedTrafficStatsEntry ::= SEQUENCE {
    snL4WebServerPort
		INTEGER,
    snL4WebClientPort
		INTEGER,
	snL4WebUncachedTxPkts
		Counter,
	snL4WebUncachedRxPkts
		Counter,
	snL4WebUncachedTxOctets
		Counter,
	snL4WebUncachedRxOctets
		Counter,
    snL4WebServerPortName
		DisplayString,
    snL4WebClientPortName
		DisplayString
	}

snL4WebServerPort 			OBJECT-TYPE
	SYNTAX  INTEGER 
	ACCESS  read-only
	STATUS  mandatory
	DESCRIPTION
		"Web Server Port."
	::= { snL4WebUncachedTrafficStatsEntry 1 }

snL4WebClientPort 			OBJECT-TYPE
	SYNTAX  INTEGER 
	ACCESS  read-only
	STATUS  mandatory
	DESCRIPTION
		"Web Client Port."
	::= { snL4WebUncachedTrafficStatsEntry 2 }

snL4WebUncachedTxPkts 		OBJECT-TYPE
	SYNTAX	Counter
	ACCESS  read-only
	STATUS  mandatory
	DESCRIPTION
		"Number of the Packets sending from Client port to Web Server port"
	::= { snL4WebUncachedTrafficStatsEntry 3 }

snL4WebUncachedRxPkts 		OBJECT-TYPE
	SYNTAX	Counter
	ACCESS  read-only
	STATUS  mandatory
	DESCRIPTION
		"Number of the Packets sending from Web Server port to Client port"
	::= { snL4WebUncachedTrafficStatsEntry 4 }

snL4WebUncachedTxOctets 	OBJECT-TYPE
	SYNTAX	Counter
	ACCESS  read-only
	STATUS  mandatory
	DESCRIPTION
		"Number of the Octets sending from Client port to Web Server port"
	::= { snL4WebUncachedTrafficStatsEntry 5 }

snL4WebUncachedRxOctets 	OBJECT-TYPE
	SYNTAX	Counter
	ACCESS  read-only
	STATUS  mandatory
	DESCRIPTION
		"Number of the Octets sending from Web Server port to Client port"
	::= { snL4WebUncachedTrafficStatsEntry 6 }

snL4WebServerPortName OBJECT-TYPE
	SYNTAX	DisplayString (SIZE(0..16))
	ACCESS	read-only
	STATUS	mandatory
	DESCRIPTION
		"Web Server Port Name string."
	::= { snL4WebUncachedTrafficStatsEntry 7 }

snL4WebClientPortName OBJECT-TYPE
	SYNTAX	DisplayString (SIZE(0..16))
	ACCESS	read-only
	STATUS	mandatory
	DESCRIPTION
		"Web Client Port Name string."
	::= { snL4WebUncachedTrafficStatsEntry 8 }


-- Web Cache Server Port table

snL4WebCachePortTable	       OBJECT-TYPE
	SYNTAX	SEQUENCE OF SnL4WebCachePortEntry
	ACCESS  not-accessible
	STATUS  mandatory
	DESCRIPTION
		"Real Server Port table."
	::= { snL4WebCachePort 1 }

snL4WebCachePortEntry	       OBJECT-TYPE
	SYNTAX	SnL4WebCachePortEntry
	ACCESS  not-accessible
	STATUS  mandatory
	DESCRIPTION
		"An entry in the Real Server Port table."
	INDEX	{ snL4WebCachePortServerIp, snL4WebCachePortPort }
	::= { snL4WebCachePortTable 1 }

SnL4WebCachePortEntry ::= SEQUENCE {
    snL4WebCachePortServerIp
		IpAddress,
    snL4WebCachePortPort
		INTEGER,
	snL4WebCachePortAdminStatus
		L4Status,
	snL4WebCachePortRowStatus
		L4RowSts,
    snL4WebCachePortDeleteState
		L4DeleteState
	}


snL4WebCachePortServerIp 	OBJECT-TYPE
	SYNTAX  IpAddress
	ACCESS  read-only
	STATUS  mandatory
	DESCRIPTION
		"Cache Server IP Address."
	::= { snL4WebCachePortEntry 1 }

snL4WebCachePortPort 		OBJECT-TYPE
    SYNTAX  INTEGER (0..65535)
	ACCESS  read-only
	STATUS  mandatory
	DESCRIPTION
		"The WEB Cache port is one of the protocol port such as UDP, TCP etc."
	::= { snL4WebCachePortEntry 2 }

snL4WebCachePortAdminStatus		       OBJECT-TYPE
	SYNTAX	L4Status
	ACCESS  read-write
	STATUS  mandatory
	DESCRIPTION
		""
	::= { snL4WebCachePortEntry 3 }

 snL4WebCachePortRowStatus	 	       OBJECT-TYPE
	SYNTAX 	L4RowSts	
	ACCESS  read-write
	STATUS  mandatory
	DESCRIPTION
		"To create or delete a Real server  port entry."
	::= { snL4WebCachePortEntry 4 }

snL4WebCachePortDeleteState	OBJECT-TYPE
	SYNTAX	L4DeleteState
	ACCESS  read-only
	STATUS  mandatory
	DESCRIPTION
		"Delete operation state." 
	::= { snL4WebCachePortEntry 5 }

-- Real Server Configuration table 

snL4RealServerCfgTable  OBJECT-TYPE
	SYNTAX	SEQUENCE OF SnL4RealServerCfgEntry
	ACCESS  not-accessible
	STATUS  mandatory
	DESCRIPTION
		"Real Server table."
	::= { snL4RealServerCfg 1 }

snL4RealServerCfgEntry  OBJECT-TYPE
	SYNTAX	SnL4RealServerCfgEntry
	ACCESS  not-accessible
	STATUS  mandatory
	DESCRIPTION
		"An entry in the Real Server table."
	INDEX	{ snL4RealServerCfgIP }
	::= { snL4RealServerCfgTable 1 }

SnL4RealServerCfgEntry ::= SEQUENCE {
    snL4RealServerCfgIP
		IpAddress,
    snL4RealServerCfgName
        L4ServerName,
    snL4RealServerCfgAdminStatus
        L4Status,
	snL4RealServerCfgMaxConnections
		INTEGER,
	snL4RealServerCfgWeight
		INTEGER,
	snL4RealServerCfgRowStatus
		L4RowSts,
    snL4RealServerCfgDeleteState
        L4DeleteState
	}

snL4RealServerCfgIP		OBJECT-TYPE
	SYNTAX IpAddress
	ACCESS  read-only
	STATUS  mandatory
	DESCRIPTION
		"Real Server IP Address."
	::= { snL4RealServerCfgEntry 1 }
snL4RealServerCfgName  OBJECT-TYPE
	SYNTAX	L4ServerName
	ACCESS  read-write
	STATUS  mandatory
	DESCRIPTION
		"Real server name."
	::= { snL4RealServerCfgEntry 2 }

snL4RealServerCfgAdminStatus	OBJECT-TYPE
	SYNTAX	L4Status
	ACCESS  read-write
	STATUS  mandatory
	DESCRIPTION
		"Real Server status is ether disabled(0) or enabled(1)."
	::= { snL4RealServerCfgEntry 3 }

snL4RealServerCfgMaxConnections 	OBJECT-TYPE
	SYNTAX	INTEGER	 (0..1000000)
	ACCESS  read-write
	STATUS  mandatory
	DESCRIPTION
		"Real Server Maximum Connection allowed."
	::= { snL4RealServerCfgEntry 4 }

 snL4RealServerCfgWeight	OBJECT-TYPE
	SYNTAX	INTEGER	  (1..20)
	ACCESS  read-write
	STATUS  mandatory
	DESCRIPTION
		"Real Server weight"
	::= { snL4RealServerCfgEntry 5 }

 snL4RealServerCfgRowStatus OBJECT-TYPE
	SYNTAX  L4RowSts
	ACCESS  read-write
	STATUS  mandatory
	DESCRIPTION
		"To create or delete a real server entry."
	::= {snL4RealServerCfgEntry  6 }

snL4RealServerCfgDeleteState	OBJECT-TYPE
	SYNTAX	L4DeleteState
	ACCESS  read-only
	STATUS  mandatory
	DESCRIPTION
		"Delete operation state." 
	::= { snL4RealServerCfgEntry 7 }


-- Real Server Port Statistic table

snL4RealServerPortCfgTable	       OBJECT-TYPE
	SYNTAX	SEQUENCE OF SnL4RealServerPortCfgEntry
	ACCESS  not-accessible
	STATUS  mandatory
	DESCRIPTION
		"Real Server Port table."
	::= { snL4RealServerPortCfg 1 }

snL4RealServerPortCfgEntry	       OBJECT-TYPE
	SYNTAX	SnL4RealServerPortCfgEntry
	ACCESS  not-accessible
	STATUS  mandatory
	DESCRIPTION
		"An entry in the Real Server Port table."
	INDEX	{snL4RealServerPortCfgIP,snL4RealServerPortCfgPort  }
	::= { snL4RealServerPortCfgTable 1 }

SnL4RealServerPortCfgEntry ::= SEQUENCE {
	snL4RealServerPortCfgIP
		IpAddress,
	snL4RealServerPortCfgPort
		INTEGER,
	snL4RealServerPortCfgServerName
        L4ServerName,
	snL4RealServerPortCfgAdminStatus
		L4Status,
	snL4RealServerPortCfgRowStatus
		L4RowSts,
    snL4RealServerPortCfgDeleteState
        L4DeleteState
	}


snL4RealServerPortCfgIP	       OBJECT-TYPE
	SYNTAX IpAddress
	ACCESS  read-only
	STATUS  mandatory
	DESCRIPTION
		"The IP address for the Real Server ."
	::= { snL4RealServerPortCfgEntry 1 }

snL4RealServerPortCfgPort       OBJECT-TYPE
	SYNTAX	INTEGER	 (0..65535)
	ACCESS  read-only
	STATUS  mandatory
	DESCRIPTION
		""
	::= { snL4RealServerPortCfgEntry 3 }


snL4RealServerPortCfgServerName	       OBJECT-TYPE
	SYNTAX	L4ServerName
	ACCESS  read-only
	STATUS  mandatory
	DESCRIPTION
		""
	::= { snL4RealServerPortCfgEntry 2 }

snL4RealServerPortCfgAdminStatus		       OBJECT-TYPE
	SYNTAX	L4Status
	ACCESS  read-write
	STATUS  mandatory
	DESCRIPTION
		""
	::= { snL4RealServerPortCfgEntry 4 }

 snL4RealServerPortCfgRowStatus	 	       OBJECT-TYPE
	SYNTAX L4RowSts	
	ACCESS  read-write
	STATUS  mandatory
	DESCRIPTION
		"To create or delete a Real server  port entry."
	::= { snL4RealServerPortCfgEntry 5 }

snL4RealServerPortCfgDeleteState	OBJECT-TYPE
	SYNTAX	L4DeleteState
	ACCESS  read-only
	STATUS  mandatory
	DESCRIPTION
		"Delete operation state." 
	::= { snL4RealServerPortCfgEntry 6 }


-- Virtual Server Configuration table

snL4VirtualServerCfgTable  OBJECT-TYPE
	SYNTAX	SEQUENCE OF SnL4VirtualServerCfgEntry
	ACCESS  not-accessible
	STATUS  mandatory
	DESCRIPTION
		"Virtual Server table."
	::= { snL4VirtualServerCfg 1 }

snL4VirtualServerCfgEntry  OBJECT-TYPE
	SYNTAX	SnL4VirtualServerCfgEntry
	ACCESS  not-accessible
	STATUS  mandatory
	DESCRIPTION
		"An entry in L4 Virtual Server table."
	INDEX	{snL4VirtualServerCfgVirtualIP  }
	::= { snL4VirtualServerCfgTable 1 }

SnL4VirtualServerCfgEntry ::= SEQUENCE {
    snL4VirtualServerCfgVirtualIP
		IpAddress,
    snL4VirtualServerCfgName
        L4ServerName,
    snL4VirtualServerCfgAdminStatus
        L4Status,
	snL4VirtualServerCfgSDAType
		INTEGER,
	snL4VirtualServerCfgRowStatus
		L4RowSts,
    snL4VirtualServerCfgDeleteState
        L4DeleteState
	}

snL4VirtualServerCfgVirtualIP  	OBJECT-TYPE
	SYNTAX IpAddress
	ACCESS  read-only
	STATUS  mandatory
	DESCRIPTION
		"Virtual Server IP Address."
	::= { snL4VirtualServerCfgEntry 1 }

snL4VirtualServerCfgName  OBJECT-TYPE
	SYNTAX	L4ServerName
	ACCESS  read-write
	STATUS  mandatory
	DESCRIPTION
		"Virtual server name."
	::= { snL4VirtualServerCfgEntry 2 }

snL4VirtualServerCfgAdminStatus	OBJECT-TYPE
	SYNTAX	L4Status
	ACCESS  read-write
	STATUS  mandatory
	DESCRIPTION
		"Virtual Server status is ether disabled(0) or enabled(1)."
	::= { snL4VirtualServerCfgEntry 3 }

snL4VirtualServerCfgSDAType  OBJECT-TYPE
	SYNTAX	 INTEGER {
		default(0),
	    leastconnection(1),
	    roundrobin(2),
	    weighted(3)
	}
	ACCESS  read-write
	STATUS  mandatory
	DESCRIPTION
		"TCP/UDP Sessions Distribution Algorithms Type."
	::= { snL4VirtualServerCfgEntry 4 }

 snL4VirtualServerCfgRowStatus OBJECT-TYPE
	SYNTAX  L4RowSts
	ACCESS  read-write
	STATUS  mandatory
	DESCRIPTION
		"To create or delete a virtual server
		entry."
	::= {snL4VirtualServerCfgEntry  5 }

snL4VirtualServerCfgDeleteState	OBJECT-TYPE
	SYNTAX	L4DeleteState
	ACCESS  read-only
	STATUS  mandatory
	DESCRIPTION
		"Delete operation state." 
	::= { snL4VirtualServerCfgEntry 6 }


-- Virtual Server Port Configuration table

snL4VirtualServerPortCfgTable	       OBJECT-TYPE
	SYNTAX	SEQUENCE OF SnL4VirtualServerPortCfgEntry
	ACCESS  not-accessible
	STATUS  mandatory
	DESCRIPTION
		"Virtual Server Port table."
	::= { snL4VirtualServerPortCfg 1 }

snL4VirtualServerPortCfgEntry	       OBJECT-TYPE
	SYNTAX	SnL4VirtualServerPortCfgEntry
	ACCESS  not-accessible
	STATUS  mandatory
	DESCRIPTION
		"An entry in the Virtual Server Port table."
	INDEX	{snL4VirtualServerPortCfgIP, snL4VirtualServerPortCfgPort  }
	::= { snL4VirtualServerPortCfgTable 1 }

SnL4VirtualServerPortCfgEntry ::= SEQUENCE {
	snL4VirtualServerPortCfgIP
		IpAddress,
	snL4VirtualServerPortCfgPort
		INTEGER,
	snL4VirtualServerPortCfgServerName
        L4ServerName,
	snL4VirtualServerPortCfgAdminStatus
		L4Status,
	snL4VirtualServerPortCfgSticky
		INTEGER,
	snL4VirtualServerPortCfgConcurrent
		INTEGER,
	snL4VirtualServerPortCfgRowStatus
		L4RowSts,
    snL4VirtualServerPortCfgDeleteState
        L4DeleteState
	}


snL4VirtualServerPortCfgIP       OBJECT-TYPE
	SYNTAX IpAddress
	ACCESS  read-only
	STATUS  mandatory
	DESCRIPTION
		"Virtual Server IP Address."
	::= { snL4VirtualServerPortCfgEntry 1 }

snL4VirtualServerPortCfgPort       OBJECT-TYPE
	SYNTAX	INTEGER	  (0..65535)
	ACCESS  read-only
	STATUS  mandatory
	DESCRIPTION
		""
	::= { snL4VirtualServerPortCfgEntry 2 }


snL4VirtualServerPortCfgServerName	       OBJECT-TYPE
	SYNTAX	L4ServerName
	ACCESS  read-only
	STATUS  mandatory
	DESCRIPTION
		""
	::= { snL4VirtualServerPortCfgEntry 3 }

snL4VirtualServerPortCfgAdminStatus		       OBJECT-TYPE
	SYNTAX	L4Status
	ACCESS  read-write
	STATUS  mandatory
	DESCRIPTION
		""
	::= { snL4VirtualServerPortCfgEntry 4 }


 snL4VirtualServerPortCfgSticky       OBJECT-TYPE
	 SYNTAX  INTEGER {
			disabled(0),
			enabled(1)       
			}
	ACCESS  read-write
	STATUS  mandatory
	DESCRIPTION
		""
	::= { snL4VirtualServerPortCfgEntry 5 }


 snL4VirtualServerPortCfgConcurrent       OBJECT-TYPE
	 SYNTAX  INTEGER {
			disabled(0),
			enabled(1)       
			}
	ACCESS  read-write
	STATUS  mandatory
	DESCRIPTION
		""
	::= { snL4VirtualServerPortCfgEntry 6 }


 snL4VirtualServerPortCfgRowStatus	 	       OBJECT-TYPE
	SYNTAX L4RowSts	
	ACCESS  read-write
	STATUS  mandatory
	DESCRIPTION
		"To create or delete a virtual server  port entry."
	::= { snL4VirtualServerPortCfgEntry 7 }

snL4VirtualServerPortCfgDeleteState	OBJECT-TYPE
	SYNTAX	L4DeleteState
	ACCESS  read-only
	STATUS  mandatory
	DESCRIPTION
		"Delete operation state." 
	::= { snL4VirtualServerPortCfgEntry 8 }



-- Virtual Server Statistic table

snL4VirtualServerStatisticTable  OBJECT-TYPE
	SYNTAX	SEQUENCE OF SnL4VirtualServerStatisticEntry
	ACCESS  not-accessible
	STATUS  mandatory
	DESCRIPTION
		"Virtual Server Statistic table."
	::= { snL4VirtualServerStatistic 1 }

snL4VirtualServerStatisticEntry  OBJECT-TYPE
	SYNTAX	SnL4VirtualServerStatisticEntry
	ACCESS  not-accessible
	STATUS  mandatory
	DESCRIPTION
		"An entry in L4 Virtual Server Statistic table."
	INDEX	{snL4VirtualServerStatisticIP  }
	::= { snL4VirtualServerStatisticTable 1 }

SnL4VirtualServerStatisticEntry ::= SEQUENCE {
	snL4VirtualServerStatisticIP 
		IpAddress,
    snL4VirtualServerStatisticName
        L4ServerName,
	snL4VirtualServerStatisticReceivePkts
		Counter,
	snL4VirtualServerStatisticTransmitPkts
		Counter,
	snL4VirtualServerStatisticTotalConnections
		Counter,
	snL4VirtualServerStatisticReceiveBytes
	   Counter64,
	snL4VirtualServerStatisticTransmitBytes
	   Counter64,
	snL4VirtualServerStatisticSymmetricState
	   INTEGER,
	snL4VirtualServerStatisticSymmetricPriority
	   INTEGER,
	snL4VirtualServerStatisticSymmetricKeep
	   INTEGER,
	snL4VirtualServerStatisticSymmetricActivates
	   Counter,
	snL4VirtualServerStatisticSymmetricInactives
	   Counter,
	snL4VirtualServerStatisticSymmetricBestStandbyMacAddr
	   PhysAddress,
	snL4VirtualServerStatisticSymmetricActiveMacAddr
	   PhysAddress
	}

snL4VirtualServerStatisticIP  OBJECT-TYPE
	SYNTAX IpAddress
	ACCESS  read-only
	STATUS  mandatory
	DESCRIPTION
		"The table index for a Virtual Server  Statistic entry."
	::= { snL4VirtualServerStatisticEntry 1 }


snL4VirtualServerStatisticName  OBJECT-TYPE
	SYNTAX	L4ServerName
	ACCESS  read-only
	STATUS  mandatory
	DESCRIPTION
		"Virtual server name."
	::= { snL4VirtualServerStatisticEntry 2 }


snL4VirtualServerStatisticReceivePkts  OBJECT-TYPE
	SYNTAX	Counter
	ACCESS	read-only
	STATUS  mandatory
	DESCRIPTION
		"" 
	::= { snL4VirtualServerStatisticEntry 3 }

snL4VirtualServerStatisticTransmitPkts  OBJECT-TYPE
	SYNTAX	Counter
	ACCESS	read-only
	STATUS  mandatory
	DESCRIPTION
		"" 
	::= { snL4VirtualServerStatisticEntry 4 }

snL4VirtualServerStatisticTotalConnections  OBJECT-TYPE
	SYNTAX	Counter
	ACCESS	read-only
	STATUS  mandatory
	DESCRIPTION
		"" 
	::= { snL4VirtualServerStatisticEntry 5 }

snL4VirtualServerStatisticReceiveBytes  OBJECT-TYPE
	SYNTAX	Counter64
	ACCESS	read-only
	STATUS  mandatory
	DESCRIPTION
		"" 
	::= { snL4VirtualServerStatisticEntry 6 }

snL4VirtualServerStatisticTransmitBytes  OBJECT-TYPE
	SYNTAX	Counter64
	ACCESS	read-only
	STATUS  mandatory
	DESCRIPTION
		"" 
	::= { snL4VirtualServerStatisticEntry 7 }

snL4VirtualServerStatisticSymmetricState  OBJECT-TYPE
	SYNTAX	INTEGER
	ACCESS	read-only
	STATUS  mandatory
	DESCRIPTION
		"" 
	::= { snL4VirtualServerStatisticEntry 8 }

snL4VirtualServerStatisticSymmetricPriority  OBJECT-TYPE
	SYNTAX	INTEGER
	ACCESS	read-only
	STATUS  mandatory
	DESCRIPTION
		"" 
	::= { snL4VirtualServerStatisticEntry 9 }

snL4VirtualServerStatisticSymmetricKeep  OBJECT-TYPE
	SYNTAX	INTEGER
	ACCESS	read-only
	STATUS  mandatory
	DESCRIPTION
		"" 
	::= { snL4VirtualServerStatisticEntry 10 }

snL4VirtualServerStatisticSymmetricActivates  OBJECT-TYPE
	SYNTAX	Counter
	ACCESS	read-only
	STATUS  mandatory
	DESCRIPTION
		"" 
	::= { snL4VirtualServerStatisticEntry 11 }

snL4VirtualServerStatisticSymmetricInactives  OBJECT-TYPE
	SYNTAX	Counter
	ACCESS	read-only
	STATUS  mandatory
	DESCRIPTION
		"" 
	::= { snL4VirtualServerStatisticEntry 12 }

snL4VirtualServerStatisticSymmetricBestStandbyMacAddr  OBJECT-TYPE
	SYNTAX	PhysAddress
	ACCESS	read-only
	STATUS  mandatory
	DESCRIPTION
		"" 
	::= { snL4VirtualServerStatisticEntry 13 }

snL4VirtualServerStatisticSymmetricActiveMacAddr  OBJECT-TYPE
	SYNTAX	PhysAddress
	ACCESS	read-only
	STATUS  mandatory
	DESCRIPTION
		"" 
	::= { snL4VirtualServerStatisticEntry 14 }


-- Real Server Statistic Table

snL4RealServerStatisticTable  OBJECT-TYPE
	SYNTAX	SEQUENCE OF SnL4RealServerStatisticEntry
	ACCESS  not-accessible
	STATUS  mandatory
	DESCRIPTION
		"Real Server Statistic table."
	::= { snL4RealServerStatistic 1 }

snL4RealServerStatisticEntry  OBJECT-TYPE
	SYNTAX	SnL4RealServerStatisticEntry
	ACCESS  not-accessible
	STATUS  mandatory
	DESCRIPTION
		"An entry in the Real Server Statistic table."
	INDEX	{snL4RealServerStatisticRealIP  }
	::= { snL4RealServerStatisticTable 1 }

SnL4RealServerStatisticEntry ::= SEQUENCE {
    snL4RealServerStatisticRealIP 
		IpAddress,
    snL4RealServerStatisticName
        L4ServerName,
	snL4RealServerStatisticReceivePkts
		Counter,
	snL4RealServerStatisticTransmitPkts
		Counter,
	snL4RealServerStatisticCurConnections
		INTEGER,
	snL4RealServerStatisticTotalConnections
		Counter,
	snL4RealServerStatisticAge
		INTEGER,
	snL4RealServerStatisticState
		INTEGER,
	snL4RealServerStatisticReassignments
		INTEGER,
	snL4RealServerStatisticReassignmentLimit
		INTEGER,
	snL4RealServerStatisticFailedPortExists
		INTEGER,
	snL4RealServerStatisticFailTime
		INTEGER,
	snL4RealServerStatisticPeakConnections
		INTEGER
	}

snL4RealServerStatisticRealIP OBJECT-TYPE
	SYNTAX	IpAddress
	ACCESS  read-only
	STATUS  mandatory
	DESCRIPTION
		""
	::= { snL4RealServerStatisticEntry 1 }


snL4RealServerStatisticName OBJECT-TYPE
	SYNTAX	L4ServerName
	ACCESS  read-only
	STATUS  mandatory
	DESCRIPTION
		""
	::= { snL4RealServerStatisticEntry 2 }

snL4RealServerStatisticReceivePkts	  OBJECT-TYPE
	SYNTAX	Counter
	ACCESS  read-only
	STATUS  mandatory
	DESCRIPTION
		""
	::= { snL4RealServerStatisticEntry 3 }

snL4RealServerStatisticTransmitPkts  OBJECT-TYPE
	SYNTAX	Counter
	ACCESS  read-only
	STATUS  mandatory
	DESCRIPTION
		""
	::= { snL4RealServerStatisticEntry 4 }

snL4RealServerStatisticCurConnections   OBJECT-TYPE
	SYNTAX	INTEGER
	ACCESS  read-only
	STATUS  mandatory
	DESCRIPTION
		""
	::= { snL4RealServerStatisticEntry 5 }

snL4RealServerStatisticTotalConnections   OBJECT-TYPE
	SYNTAX	Counter
	ACCESS  read-only
	STATUS  mandatory
	DESCRIPTION
		""
	::= { snL4RealServerStatisticEntry 6 }

snL4RealServerStatisticAge  OBJECT-TYPE
	SYNTAX	INTEGER
	ACCESS  read-only
	STATUS  mandatory
	DESCRIPTION
		""
	::= { snL4RealServerStatisticEntry 7 }

snL4RealServerStatisticState  OBJECT-TYPE
	SYNTAX	INTEGER	{
	serverdisabled(0),
	serverenabled(1),
	serverfailed(2),
	servertesting(3),
	serversuspect(4),
	servershutdown(5),
	serveractive(6)
	}
	ACCESS  read-only
	STATUS  mandatory
	DESCRIPTION
		""
	::= { snL4RealServerStatisticEntry 8 }

snL4RealServerStatisticReassignments  OBJECT-TYPE
	SYNTAX	INTEGER
	ACCESS  read-only
	STATUS  mandatory
	DESCRIPTION
		""
	::= { snL4RealServerStatisticEntry 9 }

snL4RealServerStatisticReassignmentLimit  OBJECT-TYPE
	SYNTAX	INTEGER
	ACCESS  read-only
	STATUS  mandatory
	DESCRIPTION
		""
	::= { snL4RealServerStatisticEntry 10 }

snL4RealServerStatisticFailedPortExists  OBJECT-TYPE
	SYNTAX	INTEGER
	ACCESS  read-only
	STATUS  mandatory
	DESCRIPTION
		""
	::= { snL4RealServerStatisticEntry 11 }

snL4RealServerStatisticFailTime  OBJECT-TYPE
	SYNTAX	INTEGER
	ACCESS  read-only
	STATUS  mandatory
	DESCRIPTION
		""
	::= { snL4RealServerStatisticEntry 12 }


snL4RealServerStatisticPeakConnections   OBJECT-TYPE
	SYNTAX	INTEGER
	ACCESS  read-only
	STATUS  mandatory
	DESCRIPTION
		""
	::= { snL4RealServerStatisticEntry 13 }




-- Virtual Server Port Statistic table

snL4VirtualServerPortStatisticTable	       OBJECT-TYPE
	SYNTAX	SEQUENCE OF SnL4VirtualServerPortStatisticEntry
	ACCESS  not-accessible
	STATUS  mandatory
	DESCRIPTION
		"Virtual Server Port Statistic table."
	::= { snL4VirtualServerPortStatistic 1 }

snL4VirtualServerPortStatisticEntry	       OBJECT-TYPE
	SYNTAX	SnL4VirtualServerPortStatisticEntry
	ACCESS  not-accessible
	STATUS  mandatory
	DESCRIPTION
		"An entry in the Virtual Server Port Statistic table."
	INDEX	{ snL4VirtualServerPortStatisticIP,snL4VirtualServerPortStatisticPort }
	::= { snL4VirtualServerPortStatisticTable 1 }

SnL4VirtualServerPortStatisticEntry ::= SEQUENCE {
	snL4VirtualServerPortStatisticIP
		IpAddress,
	snL4VirtualServerPortStatisticPort
		INTEGER,
	snL4VirtualServerPortStatisticServerName
        L4ServerName,
	snL4VirtualServerPortStatisticCurrentConnection
		INTEGER,
	snL4VirtualServerPortStatisticTotalConnection
		Counter,
	snL4VirtualServerPortStatisticPeakConnection
		INTEGER
	}

snL4VirtualServerPortStatisticIP	       OBJECT-TYPE
	SYNTAX	IpAddress
	ACCESS  read-only
	STATUS  mandatory
	DESCRIPTION
		"The index for Virtual Server Port Statistic entry."
	::= { snL4VirtualServerPortStatisticEntry 1 }

snL4VirtualServerPortStatisticPort   OBJECT-TYPE
	SYNTAX	INTEGER	 (1..2048)
	ACCESS  read-only
	STATUS  mandatory
	DESCRIPTION
		""
	::= { snL4VirtualServerPortStatisticEntry 2 }

 snL4VirtualServerPortStatisticServerName 	       OBJECT-TYPE
	SYNTAX	L4ServerName
	ACCESS  read-only
	STATUS  mandatory
	DESCRIPTION
		""
	::= { snL4VirtualServerPortStatisticEntry 3 }

 snL4VirtualServerPortStatisticCurrentConnection 	       OBJECT-TYPE
	SYNTAX	INTEGER
	ACCESS  read-only
	STATUS  mandatory
	DESCRIPTION
		""
	::= { snL4VirtualServerPortStatisticEntry 4 }

 snL4VirtualServerPortStatisticTotalConnection		       OBJECT-TYPE
	SYNTAX	Counter
	ACCESS  read-only
	STATUS  mandatory
	DESCRIPTION
		""
	::= { snL4VirtualServerPortStatisticEntry 5 }

 snL4VirtualServerPortStatisticPeakConnection 	       OBJECT-TYPE
	SYNTAX	INTEGER
	ACCESS  read-only
	STATUS  mandatory
	DESCRIPTION
		""
	::= { snL4VirtualServerPortStatisticEntry 6 }

-- Real Server Port Statistic table

snL4RealServerPortStatisticTable	       OBJECT-TYPE
	SYNTAX	SEQUENCE OF SnL4RealServerPortStatisticEntry
	ACCESS  not-accessible
	STATUS  mandatory
	DESCRIPTION
		"Real Server Port Statistic table."
	::= { snL4RealServerPortStatistic 1 }

snL4RealServerPortStatisticEntry	       OBJECT-TYPE
	SYNTAX	SnL4RealServerPortStatisticEntry
	ACCESS  not-accessible
	STATUS  mandatory
	DESCRIPTION
		"An entry in the Real Server Port Statistic table."
	INDEX	{ snL4RealServerPortStatisticIP,snL4RealServerPortStatisticPort }
	::= { snL4RealServerPortStatisticTable 1 }

SnL4RealServerPortStatisticEntry ::= SEQUENCE {
	snL4RealServerPortStatisticIP
		IpAddress,
	snL4RealServerPortStatisticPort
		INTEGER,
	snL4RealServerPortStatisticServerName
        L4ServerName,
	snL4RealServerPortStatisticReassignCount
		INTEGER,
	snL4RealServerPortStatisticState
		INTEGER,
	snL4RealServerPortStatisticFailTime
		INTEGER,
	snL4RealServerPortStatisticCurrentConnection
		INTEGER,
	snL4RealServerPortStatisticTotalConnection
		Counter,
	snL4RealServerPortStatisticRxPkts
		Counter,
	snL4RealServerPortStatisticTxPkts
		Counter,
	snL4RealServerPortStatisticRxBytes
		Counter,
	snL4RealServerPortStatisticTxBytes
		Counter,
	snL4RealServerPortStatisticPeakConnection
		INTEGER
	}


snL4RealServerPortStatisticIP	       OBJECT-TYPE
	SYNTAX IpAddress
	ACCESS  read-only
	STATUS  mandatory
	DESCRIPTION
		"The index for Real Server Port Statistic entry."
	::= { snL4RealServerPortStatisticEntry 1 }

snL4RealServerPortStatisticPort	       OBJECT-TYPE
	SYNTAX	INTEGER
	ACCESS  read-only
	STATUS  mandatory
	DESCRIPTION
		""
	::= { snL4RealServerPortStatisticEntry 2 }

snL4RealServerPortStatisticServerName	       OBJECT-TYPE
	SYNTAX	L4ServerName
	ACCESS  read-only
	STATUS  mandatory
	DESCRIPTION
		""
	::= { snL4RealServerPortStatisticEntry 3 }

snL4RealServerPortStatisticReassignCount	       OBJECT-TYPE
	SYNTAX	INTEGER
	ACCESS  read-only
	STATUS  mandatory
	DESCRIPTION
		""
	::= { snL4RealServerPortStatisticEntry 4 }

 snL4RealServerPortStatisticState	       OBJECT-TYPE
	SYNTAX	INTEGER	{
		disabled(0),
		enabled(1),
		failed(2),
		testing(3),
		suspect(4),
	    shutdown(5),
		active(6),
		unbound(7),
		awaitUnbind(8),
		awaitDelete(9)
	}
	ACCESS  read-only
	STATUS  mandatory
	DESCRIPTION
		"Real server port state"
	::= { snL4RealServerPortStatisticEntry 5 }

snL4RealServerPortStatisticFailTime 	       OBJECT-TYPE
	SYNTAX	INTEGER
	ACCESS  read-only
	STATUS  mandatory
	DESCRIPTION
		"Only useful, if real server port state is failed.
		 Indicating how seconds has been elapsed from the last retry."
 	::= { snL4RealServerPortStatisticEntry 6 }

snL4RealServerPortStatisticCurrentConnection	       OBJECT-TYPE
	SYNTAX	INTEGER
	ACCESS  read-only
	STATUS  mandatory
	DESCRIPTION
		"Real server port current connection"
	::= { snL4RealServerPortStatisticEntry 7 }

snL4RealServerPortStatisticTotalConnection	       OBJECT-TYPE
	SYNTAX	Counter
	ACCESS  read-only
	STATUS  mandatory
	DESCRIPTION
		"Real server port total connection"
	::= { snL4RealServerPortStatisticEntry 8 }

snL4RealServerPortStatisticRxPkts	       OBJECT-TYPE
	SYNTAX	Counter
	ACCESS  read-only
	STATUS  mandatory
	DESCRIPTION
		"Real server port receive packets."
	::= { snL4RealServerPortStatisticEntry 9 }


snL4RealServerPortStatisticTxPkts	       OBJECT-TYPE
	SYNTAX	Counter
	ACCESS  read-only
	STATUS  mandatory
	DESCRIPTION
		"Real server port transmit packets."
	::= { snL4RealServerPortStatisticEntry 10 }


snL4RealServerPortStatisticRxBytes	       OBJECT-TYPE
	SYNTAX	Counter
	ACCESS  read-only
	STATUS  mandatory
	DESCRIPTION
		"Real server port receive bytes."
	::= { snL4RealServerPortStatisticEntry 11 }

snL4RealServerPortStatisticTxBytes	       OBJECT-TYPE
	SYNTAX	Counter
	ACCESS  read-only
	STATUS  mandatory
	DESCRIPTION
		"Real server port transmit bytes."
	::= { snL4RealServerPortStatisticEntry 12 }


snL4RealServerPortStatisticPeakConnection	       OBJECT-TYPE
	SYNTAX	INTEGER
	ACCESS  read-only
	STATUS  mandatory
	DESCRIPTION
		"peak connection for real server port."
	::= { snL4RealServerPortStatisticEntry 13 }


-- GSLB Site Remote ServerIron Configuration table

snL4GslbSiteRemoteServerIronTable	       OBJECT-TYPE
	SYNTAX	SEQUENCE OF SnL4GslbSiteRemoteServerIronEntry
	ACCESS  not-accessible
	STATUS  mandatory
	DESCRIPTION
		"GSLB remote ServerIron configuration table."
	::= { snL4GslbSiteRemoteServerIrons 1 }

snL4GslbSiteRemoteServerIronEntry	       OBJECT-TYPE
	SYNTAX	SnL4GslbSiteRemoteServerIronEntry	
	ACCESS  not-accessible
	STATUS  mandatory
	DESCRIPTION
		"An entry of a GSLB remote ServerIron configuration."
	INDEX	{ snL4GslbSiteRemoteServerIronIP }
	::= { snL4GslbSiteRemoteServerIronTable 1 }

SnL4GslbSiteRemoteServerIronEntry ::= SEQUENCE {
	snL4GslbSiteRemoteServerIronIP
		IpAddress,
	snL4GslbSiteRemoteServerIronPreference
		INTEGER
	}


snL4GslbSiteRemoteServerIronIP	       OBJECT-TYPE
	SYNTAX IpAddress
	ACCESS  read-only
	STATUS  mandatory
	DESCRIPTION
		"The index for each remote ServerIron in a site."
	::= { snL4GslbSiteRemoteServerIronEntry 1 }

snL4GslbSiteRemoteServerIronPreference 	OBJECT-TYPE
	SYNTAX	INTEGER	(0..255)
	ACCESS  read-write
	STATUS  mandatory
	DESCRIPTION
		"The preference of a remote ServerIron. The default value is 128."
    DEFVAL { 128 }
	::= { snL4GslbSiteRemoteServerIronEntry 2 }


-- Real Server Monitor Group

-- The Real Server History Control Group

-- The snL4History control group controls the periodic statistical
-- sampling of data from various types of data sources.  The
-- snL4RealServerHistoryControlTable stores configuration entries that each
-- define an interface, polling period, and other parameters.
-- Once samples are taken, their data is stored in an entry
-- in a media-specific table.  Each such entry defines one
-- sample, and is associated with the snL4RealServerHistoryControlEntry that
-- caused the sample to be taken.  Each counter in the
-- snL4HistoryEntry counts the same event as its
-- similarly-named counterpart in the Statistics Entry,
-- except that each value here is a cumulative sum during a
-- sampling period.
--
-- If the probe keeps track of the time of day, it should
-- start the first sample of the snL4History at a time such that
-- when the next hour of the day begins, a sample is
-- started at that instant.  This tends to make more
-- user-friendly reports, and enables comparison of reports
-- from different probes that have relatively accurate time
-- of day.
--
-- The probe is encouraged to add two snL4History control entries
-- per monitored interface upon initialization that describe
-- a short term and a long term polling period.  Suggested
-- parameters are 30 seconds for the short term polling period
-- and 30 minutes for the long term period.

snL4RealServerHistoryControlTable OBJECT-TYPE
	SYNTAX SEQUENCE OF SnL4RealServerHistoryControlEntry
	ACCESS not-accessible
	STATUS mandatory
	DESCRIPTION
		"A list of history control entries."
	::= { snL4History 1 }

snL4RealServerHistoryControlEntry OBJECT-TYPE
	SYNTAX SnL4RealServerHistoryControlEntry
	ACCESS not-accessible
	STATUS mandatory
	DESCRIPTION
		"A list of parameters that set up a periodic sampling
		of statistics.As an example, an instance of the
		snL4RealServerHistoryControlInterval object might be named
		snL4RealServerHistoryControlInterval.2"
	INDEX { snL4RealServerHistoryControlIndex }
	::= { snL4RealServerHistoryControlTable 1 }

	SnL4RealServerHistoryControlEntry ::= SEQUENCE {
		snL4RealServerHistoryControlIndex			 
			INTEGER (1..65535),
		snL4RealServerHistoryControlDataSource		
			OBJECT IDENTIFIER,
		snL4RealServerHistoryControlBucketsRequested
			INTEGER (1..65535),
		snL4RealServerHistoryControlBucketsGranted	
			INTEGER (1..65535),
		snL4RealServerHistoryControlInterval		
			INTEGER (1..3600),
		snL4RealServerHistoryControlOwner			 
			DisplayString,
		snL4RealServerHistoryControlStatus			
			INTEGER
	}

snL4RealServerHistoryControlIndex OBJECT-TYPE
	SYNTAX INTEGER (1..65535)
	ACCESS read-only
	STATUS mandatory
	DESCRIPTION
		"An index that uniquely identifies an entry in the
		snL4RealServerHistoryControl table.Each such entry defines a
		set of samples at a particular interval for an
		interface on the device."
	::= { snL4RealServerHistoryControlEntry 1 }

snL4RealServerHistoryControlDataSource OBJECT-TYPE
	SYNTAX OBJECT IDENTIFIER
	ACCESS read-write
	STATUS mandatory
	DESCRIPTION
		"This object identifies the source of the data for
		which historical data was collected and
		placed in a media-specific table on behalf of this
		snL4RealServerHistoryControlEntry.This source can be any
		real/virtual server and real/virtual server port on 
		this ServerIron.  In order to identify
		a particular instance, this object shall identify
		the instance of the object, defined in the above 
		statistics tables.
	
		This object may not be modified if the associated
		snL4RealServerHistoryControlStatus object is equal to valid(1)."
	::= { snL4RealServerHistoryControlEntry 2 }

snL4RealServerHistoryControlBucketsRequested OBJECT-TYPE
	SYNTAX INTEGER (1..65535)
	ACCESS read-write
	STATUS mandatory
	DESCRIPTION
		"The requested number of discrete time intervals
		over which data is to be saved in the part of the
		media-specific table associated with this
		snL4RealServerHistoryControlEntry.
	
		When this object is created or modified, the probe
		should set snL4RealServerHistoryControlBucketsGranted as closely to
		this object as is possible for the particular probe
		implementation and available resources."
	DEFVAL { 50 }
	::= { snL4RealServerHistoryControlEntry 3 }

snL4RealServerHistoryControlBucketsGranted OBJECT-TYPE
	SYNTAX INTEGER (1..65535)
	ACCESS read-only
	STATUS mandatory
	DESCRIPTION
		"The number of discrete sampling intervals
		over which data shall be saved in the part of
		the media-specific table associated with this
		snL4RealServerHistoryControlEntry.
	
		When the associated snL4RealServerHistoryControlBucketsRequested
		object is created or modified, the probe
		should set this object as closely to the requested
		value as is possible for the particular
		probe implementation and available resources.The
		probe must not lower this value except as a result
		of a modification to the associated
		snL4RealServerHistoryControlBucketsRequested object.
	
		There will be times when the actual number of
		buckets associated with this entry is less than
		the value of this object.In this case, at the
		end of each sampling interval, a new bucket will
		be added to the media-specific table.
	
		When the number of buckets reaches the value of
		this object and a new bucket is to be added to the
		media-specific table, the oldest bucket associated
		with this snL4RealServerHistoryControlEntry shall be deleted by
		the agent so that the new bucket can be added.
	
		When the value of this object changes to a value less
		than the current value, entries are deleted
		from the media-specific table associated with this
		snL4RealServerHistoryControlEntry.Enough of the oldest of these
		entries shall be deleted by the agent so that their
		number remains less than or equal to the new value of
		this object.
	
		When the value of this object changes to a value
		greater than the current value, the number of
		associated media- specific entries may be allowed to
		grow."
	::= { snL4RealServerHistoryControlEntry 4 }

snL4RealServerHistoryControlInterval OBJECT-TYPE
	SYNTAX INTEGER (1..3600)
	ACCESS read-write
	STATUS mandatory
	DESCRIPTION
		"The interval in seconds over which the data is
		sampled for each bucket in the part of the
		media-specific table associated with this
		snL4RealServerHistoryControlEntry.This interval can
		be set to any number of seconds between 1 and
		3600 (1 hour).
	
		Because the counters in a bucket may overflow at their
		maximum value with no indication, a prudent manager
		will take into account the possibility of overflow
		in any of the associated counters.It is important
		to consider the minimum time in which any counter
		could overflow on a particular media type and set
		the snL4RealServerHistoryControlInterval object to a value less
		than this interval.This is typically most
		important for the 'octets' counter in any
		media-specific table.	
		This object may not be modified if the associated
		snL4RealServerHistoryControlStatus object is equal to valid(1)."
	DEFVAL { 1800 }
	::= { snL4RealServerHistoryControlEntry 5 }

snL4RealServerHistoryControlOwner OBJECT-TYPE
	SYNTAX DisplayString
	ACCESS read-write
	STATUS mandatory
	DESCRIPTION
		"The entity that configured this entry and is
		therefore using the resources assigned to it."
	::= { snL4RealServerHistoryControlEntry 6 }

snL4RealServerHistoryControlStatus OBJECT-TYPE
	SYNTAX INTEGER { 
				valid(1),
             	createRequest(2),
             	underCreation(3),
             	invalid(4)
           }
	ACCESS read-write
	STATUS mandatory
	DESCRIPTION
		"The status of this snL4RealServerHistoryControl entry.
		Each instance of the media-specific table associated
		with this snL4RealServerHistoryControlEntry will be deleted by the
		agent if this snL4RealServerHistoryControlEntry is not equal to
		valid(1)."
	::= { snL4RealServerHistoryControlEntry 7 }


-- The Real Server History Group


snL4RealServerHistoryTable OBJECT-TYPE
	SYNTAX SEQUENCE OF SnL4RealServerHistoryEntry
	ACCESS not-accessible
	STATUS mandatory
	DESCRIPTION
		"A list of Ethernet snL4History entries."
	::= { snL4History 2 }

snL4RealServerHistoryEntry OBJECT-TYPE
	SYNTAX SnL4RealServerHistoryEntry
	ACCESS not-accessible
	STATUS mandatory
	DESCRIPTION
		"An historical sample of Ethernet statistics on a
		particular Ethernet interface.  This sample is
		associated with the snL4RealServerHistoryControlEntry which set up
		the parameters for a regular collection of these
		samples.  As an example, an instance of the
		snL4RealServerHistoryReceivePkts object might be named
		snL4RealServerHistoryReceivePkts.2.89"
	INDEX { snL4RealServerHistoryIndex , snL4RealServerHistorySampleIndex }
	::= { snL4RealServerHistoryTable 1 }

SnL4RealServerHistoryEntry ::= SEQUENCE {
	snL4RealServerHistoryIndex                 
		INTEGER (1..65535),
	snL4RealServerHistorySampleIndex           
		INTEGER (1..2147483647),
	snL4RealServerHistoryIntervalStart         
		TimeTicks,
	snL4RealServerHistoryReceivePkts
		Counter,
	snL4RealServerHistoryTransmitPkts
		Counter,
	snL4RealServerHistoryTotalConnections
		Counter,
	snL4RealServerHistoryCurConnections
		INTEGER,
	snL4RealServerHistoryPeakConnections
		INTEGER,
	snL4RealServerHistoryReassignments
		INTEGER
    }

snL4RealServerHistoryIndex OBJECT-TYPE
	SYNTAX INTEGER (1..65535)
	ACCESS read-only
	STATUS mandatory
	DESCRIPTION
		"The snL4RealServerHistory of which this entry is a part.The
		snL4RealServerHistory identified by a particular value of this
		index is the same snL4RealServerHistory as identified
		by the same value of snL4RealServerHistoryControlIndex."
	::= { snL4RealServerHistoryEntry 1 }

snL4RealServerHistorySampleIndex OBJECT-TYPE
	SYNTAX INTEGER (1..2147483647)
	ACCESS read-only
	STATUS mandatory
	DESCRIPTION
		"An index that uniquely identifies the particular
		sample this entry represents among all samples
		associated with the same snL4RealServerHistoryControlEntry.
		This index starts at 1 and increases by one
		as each new sample is taken."
	::= { snL4RealServerHistoryEntry 2 }

snL4RealServerHistoryIntervalStart OBJECT-TYPE
	SYNTAX TimeTicks
	ACCESS read-only
	STATUS mandatory
	DESCRIPTION
		"The value of sysUpTime at the start of the interval
		over which this sample was measured.If the probe
		keeps track of the time of day, it should start
		the first sample of the snL4RealServerHistory at a time such that
		when the next hour of the day begins, a sample is
		started at that instant.Note that following this
		rule may require the probe to delay collecting the
		first sample of the snL4RealServerHistory, as each sample must be
		of the same interval.Also note that the sample which
		is currently being collected is not accessible in this
		table until the end of its interval."
	::= { snL4RealServerHistoryEntry 3 }


snL4RealServerHistoryReceivePkts	  OBJECT-TYPE
	SYNTAX	Counter
	ACCESS  read-only
	STATUS  mandatory
	DESCRIPTION
		""
	::= { snL4RealServerHistoryEntry 4 }

snL4RealServerHistoryTransmitPkts  OBJECT-TYPE
	SYNTAX	Counter
	ACCESS  read-only
	STATUS  mandatory
	DESCRIPTION
		""
	::= { snL4RealServerHistoryEntry 5 }

snL4RealServerHistoryTotalConnections   OBJECT-TYPE
	SYNTAX	Counter
	ACCESS  read-only
	STATUS  mandatory
	DESCRIPTION
		""
	::= { snL4RealServerHistoryEntry 6 }

snL4RealServerHistoryCurConnections   OBJECT-TYPE
	SYNTAX	INTEGER
	ACCESS  read-only
	STATUS  mandatory
	DESCRIPTION
		""
	::= { snL4RealServerHistoryEntry 7 }

snL4RealServerHistoryPeakConnections   OBJECT-TYPE
	SYNTAX	INTEGER
	ACCESS  read-only
	STATUS  mandatory
	DESCRIPTION
		""
	::= { snL4RealServerHistoryEntry 8 }

snL4RealServerHistoryReassignments   OBJECT-TYPE
	SYNTAX	INTEGER
	ACCESS  read-only
	STATUS  mandatory
	DESCRIPTION
		""
	::= { snL4RealServerHistoryEntry 9 }


-- Real Server Port Monitor Group

-- The Real Server Port History Control Group

snL4RealServerPortHistoryControlTable OBJECT-TYPE
	SYNTAX SEQUENCE OF SnL4RealServerPortHistoryControlEntry
	ACCESS not-accessible
	STATUS mandatory
	DESCRIPTION
		"A list of history control entries."
	::= { snL4History 3 }

snL4RealServerPortHistoryControlEntry OBJECT-TYPE
	SYNTAX SnL4RealServerPortHistoryControlEntry
	ACCESS not-accessible
	STATUS mandatory
	DESCRIPTION
		"A list of parameters that set up a periodic sampling
		of statistics.As an example, an instance of the
		snL4RealServerPortHistoryControlInterval object might be named
		snL4RealServerPortHistoryControlInterval.2"
	INDEX { snL4RealServerPortHistoryControlIndex }
	::= { snL4RealServerPortHistoryControlTable 1 }

	SnL4RealServerPortHistoryControlEntry ::= SEQUENCE {
		snL4RealServerPortHistoryControlIndex			 
			INTEGER (1..65535),
		snL4RealServerPortHistoryControlDataSource		
			OBJECT IDENTIFIER,
		snL4RealServerPortHistoryControlBucketsRequested
			INTEGER (1..65535),
		snL4RealServerPortHistoryControlBucketsGranted	
			INTEGER (1..65535),
		snL4RealServerPortHistoryControlInterval		
			INTEGER (1..3600),
		snL4RealServerPortHistoryControlOwner			 
			DisplayString,
		snL4RealServerPortHistoryControlStatus			
			INTEGER
	}

snL4RealServerPortHistoryControlIndex OBJECT-TYPE
	SYNTAX INTEGER (1..65535)
	ACCESS read-only
	STATUS mandatory
	DESCRIPTION
		"An index that uniquely identifies an entry in the
		snL4RealServerPortHistoryControl table.Each such entry defines a
		set of samples at a particular interval for an
		interface on the device."
	::= { snL4RealServerPortHistoryControlEntry 1 }

snL4RealServerPortHistoryControlDataSource OBJECT-TYPE
	SYNTAX OBJECT IDENTIFIER
	ACCESS read-write
	STATUS mandatory
	DESCRIPTION
		"This object identifies the source of the data for
		which historical data was collected and
		placed in a media-specific table on behalf of this
		snL4RealServerPortHistoryControlEntry.This source can be any
		real/virtual server and real/virtual server port on 
		this ServerIron.  In order to identify
		a particular instance, this object shall identify
		the instance of the object, defined in the above 
		statistics tables.
	
		This object may not be modified if the associated
		snL4RealServerPortHistoryControlStatus object is equal to valid(1)."
	::= { snL4RealServerPortHistoryControlEntry 2 }

snL4RealServerPortHistoryControlBucketsRequested OBJECT-TYPE
	SYNTAX INTEGER (1..65535)
	ACCESS read-write
	STATUS mandatory
	DESCRIPTION
		"The requested number of discrete time intervals
		over which data is to be saved in the part of the
		media-specific table associated with this
		snL4RealServerPortHistoryControlEntry.
	
		When this object is created or modified, the probe
		should set snL4RealServerPortHistoryControlBucketsGranted as closely to
		this object as is possible for the particular probe
		implementation and available resources."
	DEFVAL { 50 }
	::= { snL4RealServerPortHistoryControlEntry 3 }

snL4RealServerPortHistoryControlBucketsGranted OBJECT-TYPE
	SYNTAX INTEGER (1..65535)
	ACCESS read-only
	STATUS mandatory
	DESCRIPTION
		"The number of discrete sampling intervals
		over which data shall be saved in the part of
		the media-specific table associated with this
		snL4RealServerPortHistoryControlEntry.
	
		When the associated snL4RealServerPortHistoryControlBucketsRequested
		object is created or modified, the probe
		should set this object as closely to the requested
		value as is possible for the particular
		probe implementation and available resources.The
		probe must not lower this value except as a result
		of a modification to the associated
		snL4RealServerPortHistoryControlBucketsRequested object.
	
		There will be times when the actual number of
		buckets associated with this entry is less than
		the value of this object.In this case, at the
		end of each sampling interval, a new bucket will
		be added to the media-specific table.
	
		When the number of buckets reaches the value of
		this object and a new bucket is to be added to the
		media-specific table, the oldest bucket associated
		with this snL4RealServerPortHistoryControlEntry shall be deleted by
		the agent so that the new bucket can be added.
	
		When the value of this object changes to a value less
		than the current value, entries are deleted
		from the media-specific table associated with this
		snL4RealServerPortHistoryControlEntry.Enough of the oldest of these
		entries shall be deleted by the agent so that their
		number remains less than or equal to the new value of
		this object.
	
		When the value of this object changes to a value
		greater than the current value, the number of
		associated media- specific entries may be allowed to
		grow."
	::= { snL4RealServerPortHistoryControlEntry 4 }

snL4RealServerPortHistoryControlInterval OBJECT-TYPE
	SYNTAX INTEGER (1..3600)
	ACCESS read-write
	STATUS mandatory
	DESCRIPTION
		"The interval in seconds over which the data is
		sampled for each bucket in the part of the
		media-specific table associated with this
		snL4RealServerPortHistoryControlEntry.This interval can
		be set to any number of seconds between 1 and
		3600 (1 hour).
	
		Because the counters in a bucket may overflow at their
		maximum value with no indication, a prudent manager
		will take into account the possibility of overflow
		in any of the associated counters.It is important
		to consider the minimum time in which any counter
		could overflow on a particular media type and set
		the snL4RealServerPortHistoryControlInterval object to a value less
		than this interval.This is typically most
		important for the 'octets' counter in any
		media-specific table.	
		This object may not be modified if the associated
		snL4RealServerPortHistoryControlStatus object is equal to valid(1)."
	DEFVAL { 1800 }
	::= { snL4RealServerPortHistoryControlEntry 5 }

snL4RealServerPortHistoryControlOwner OBJECT-TYPE
	SYNTAX DisplayString
	ACCESS read-write
	STATUS mandatory
	DESCRIPTION
		"The entity that configured this entry and is
		therefore using the resources assigned to it."
	::= { snL4RealServerPortHistoryControlEntry 6 }

snL4RealServerPortHistoryControlStatus OBJECT-TYPE
	SYNTAX INTEGER { 
				valid(1),
             	createRequest(2),
             	underCreation(3),
             	invalid(4)
           }
	ACCESS read-write
	STATUS mandatory
	DESCRIPTION
		"The status of this snL4RealServerPortHistoryControl entry.
		Each instance of the media-specific table associated
		with this snL4RealServerPortHistoryControlEntry will be deleted by the
		agent if this snL4RealServerPortHistoryControlEntry is not equal to
		valid(1)."
	::= { snL4RealServerPortHistoryControlEntry 7 }


-- The Real Server Port History Group


snL4RealServerPortHistoryTable OBJECT-TYPE
	SYNTAX SEQUENCE OF SnL4RealServerPortHistoryEntry
	ACCESS not-accessible
	STATUS mandatory
	DESCRIPTION
		"A list of Ethernet snL4History entries."
	::= { snL4History 4 }

snL4RealServerPortHistoryEntry OBJECT-TYPE
	SYNTAX SnL4RealServerPortHistoryEntry
	ACCESS not-accessible
	STATUS mandatory
	DESCRIPTION
		"An historical sample of Ethernet statistics on a
		particular Ethernet interface.  This sample is
		associated with the snL4RealServerPortHistoryControlEntry which set up
		the parameters for a regular collection of these
		samples.  As an example, an instance of the
		snL4RealServerPortHistoryReceivePkts object might be named
		snL4RealServerPortHistoryReceivePkts.2.89"
	INDEX { snL4RealServerPortHistoryIndex , snL4RealServerPortHistorySampleIndex }
	::= { snL4RealServerPortHistoryTable 1 }

SnL4RealServerPortHistoryEntry ::= SEQUENCE {
	snL4RealServerPortHistoryIndex                 
		INTEGER (1..65535),
	snL4RealServerPortHistorySampleIndex           
		INTEGER (1..2147483647),
	snL4RealServerPortHistoryIntervalStart         
		TimeTicks,
	snL4RealServerPortHistoryReceivePkts
		Counter,
	snL4RealServerPortHistoryTransmitPkts
		Counter,
	snL4RealServerPortHistoryTotalConnections
		Counter,
	snL4RealServerPortHistoryCurConnections
		INTEGER,
	snL4RealServerPortHistoryPeakConnections
		INTEGER,
	snL4RealServerPortHistoryResponseTime
		INTEGER
    }

snL4RealServerPortHistoryIndex OBJECT-TYPE
	SYNTAX INTEGER (1..65535)
	ACCESS read-only
	STATUS mandatory
	DESCRIPTION
		"The snL4RealServerPortHistory of which this entry is a part.The
		snL4RealServerPortHistory identified by a particular value of this
		index is the same snL4RealServerPortHistory as identified
		by the same value of snL4RealServerPortHistoryControlIndex."
	::= { snL4RealServerPortHistoryEntry 1 }

snL4RealServerPortHistorySampleIndex OBJECT-TYPE
	SYNTAX INTEGER (1..2147483647)
	ACCESS read-only
	STATUS mandatory
	DESCRIPTION
		"An index that uniquely identifies the particular
		sample this entry represents among all samples
		associated with the same snL4RealServerPortHistoryControlEntry.
		This index starts at 1 and increases by one
		as each new sample is taken."
	::= { snL4RealServerPortHistoryEntry 2 }

snL4RealServerPortHistoryIntervalStart OBJECT-TYPE
	SYNTAX TimeTicks
	ACCESS read-only
	STATUS mandatory
	DESCRIPTION
		"The value of sysUpTime at the start of the interval
		over which this sample was measured.If the probe
		keeps track of the time of day, it should start
		the first sample of the snL4RealServerPortHistory at a time such that
		when the next hour of the day begins, a sample is
		started at that instant.Note that following this
		rule may require the probe to delay collecting the
		first sample of the snL4RealServerPortHistory, as each sample must be
		of the same interval.Also note that the sample which
		is currently being collected is not accessible in this
		table until the end of its interval."
	::= { snL4RealServerPortHistoryEntry 3 }


snL4RealServerPortHistoryReceivePkts	  OBJECT-TYPE
	SYNTAX	Counter
	ACCESS  read-only
	STATUS  mandatory
	DESCRIPTION
		""
	::= { snL4RealServerPortHistoryEntry 4 }

snL4RealServerPortHistoryTransmitPkts  OBJECT-TYPE
	SYNTAX	Counter
	ACCESS  read-only
	STATUS  mandatory
	DESCRIPTION
		""
	::= { snL4RealServerPortHistoryEntry 5 }

snL4RealServerPortHistoryTotalConnections   OBJECT-TYPE
	SYNTAX	Counter
	ACCESS  read-only
	STATUS  mandatory
	DESCRIPTION
		""
	::= { snL4RealServerPortHistoryEntry 6 }

snL4RealServerPortHistoryCurConnections   OBJECT-TYPE
	SYNTAX	INTEGER
	ACCESS  read-only
	STATUS  mandatory
	DESCRIPTION
		""
	::= { snL4RealServerPortHistoryEntry 7 }

snL4RealServerPortHistoryPeakConnections   OBJECT-TYPE
	SYNTAX	INTEGER
	ACCESS  read-only
	STATUS  mandatory
	DESCRIPTION
		""
	::= { snL4RealServerPortHistoryEntry 8 }

snL4RealServerPortHistoryResponseTime   OBJECT-TYPE
	SYNTAX	INTEGER
	ACCESS  read-only
	STATUS  mandatory
	DESCRIPTION
		""
	::= { snL4RealServerPortHistoryEntry 9 }


-- Virtual Server Monitor Group
-- The Virtual Server History Control Group


snL4VirtualServerHistoryControlTable OBJECT-TYPE
	SYNTAX SEQUENCE OF SnL4VirtualServerHistoryControlEntry
	ACCESS not-accessible
	STATUS mandatory
	DESCRIPTION
		"A list of history control entries."
	::= { snL4History 5 }

snL4VirtualServerHistoryControlEntry OBJECT-TYPE
	SYNTAX SnL4VirtualServerHistoryControlEntry
	ACCESS not-accessible
	STATUS mandatory
	DESCRIPTION
		"A list of parameters that set up a periodic sampling
		of statistics.As an example, an instance of the
		snL4VirtualServerHistoryControlInterval object might be named
		snL4VirtualServerHistoryControlInterval.2"
	INDEX { snL4VirtualServerHistoryControlIndex }
	::= { snL4VirtualServerHistoryControlTable 1 }

	SnL4VirtualServerHistoryControlEntry ::= SEQUENCE {
		snL4VirtualServerHistoryControlIndex			 
			INTEGER (1..65535),
		snL4VirtualServerHistoryControlDataSource		
			OBJECT IDENTIFIER,
		snL4VirtualServerHistoryControlBucketsRequested
			INTEGER (1..65535),
		snL4VirtualServerHistoryControlBucketsGranted	
			INTEGER (1..65535),
		snL4VirtualServerHistoryControlInterval		
			INTEGER (1..3600),
		snL4VirtualServerHistoryControlOwner			 
			DisplayString,
		snL4VirtualServerHistoryControlStatus			
			INTEGER
	}

snL4VirtualServerHistoryControlIndex OBJECT-TYPE
	SYNTAX INTEGER (1..65535)
	ACCESS read-only
	STATUS mandatory
	DESCRIPTION
		"An index that uniquely identifies an entry in the
		snL4VirtualServerHistoryControl table.Each such entry defines a
		set of samples at a particular interval for an
		interface on the device."
	::= { snL4VirtualServerHistoryControlEntry 1 }

snL4VirtualServerHistoryControlDataSource OBJECT-TYPE
	SYNTAX OBJECT IDENTIFIER
	ACCESS read-write
	STATUS mandatory
	DESCRIPTION
		"This object identifies the source of the data for
		which historical data was collected and
		placed in a media-specific table on behalf of this
		snL4VirtualServerHistoryControlEntry.This source can be any
		real/virtual server and real/virtual server port on 
		this ServerIron.  In order to identify
		a particular instance, this object shall identify
		the instance of the object, defined in the above 
		statistics tables.
	
		This object may not be modified if the associated
		snL4VirtualServerHistoryControlStatus object is equal to valid(1)."
	::= { snL4VirtualServerHistoryControlEntry 2 }

snL4VirtualServerHistoryControlBucketsRequested OBJECT-TYPE
	SYNTAX INTEGER (1..65535)
	ACCESS read-write
	STATUS mandatory
	DESCRIPTION
		"The requested number of discrete time intervals
		over which data is to be saved in the part of the
		media-specific table associated with this
		snL4VirtualServerHistoryControlEntry.
	
		When this object is created or modified, the probe
		should set snL4VirtualServerHistoryControlBucketsGranted as closely to
		this object as is possible for the particular probe
		implementation and available resources."
	DEFVAL { 50 }
	::= { snL4VirtualServerHistoryControlEntry 3 }

snL4VirtualServerHistoryControlBucketsGranted OBJECT-TYPE
	SYNTAX INTEGER (1..65535)
	ACCESS read-only
	STATUS mandatory
	DESCRIPTION
		"The number of discrete sampling intervals
		over which data shall be saved in the part of
		the media-specific table associated with this
		snL4VirtualServerHistoryControlEntry.
	
		When the associated snL4VirtualServerHistoryControlBucketsRequested
		object is created or modified, the probe
		should set this object as closely to the requested
		value as is possible for the particular
		probe implementation and available resources.The
		probe must not lower this value except as a result
		of a modification to the associated
		snL4VirtualServerHistoryControlBucketsRequested object.
	
		There will be times when the actual number of
		buckets associated with this entry is less than
		the value of this object.In this case, at the
		end of each sampling interval, a new bucket will
		be added to the media-specific table.
	
		When the number of buckets reaches the value of
		this object and a new bucket is to be added to the
		media-specific table, the oldest bucket associated
		with this snL4VirtualServerHistoryControlEntry shall be deleted by
		the agent so that the new bucket can be added.
	
		When the value of this object changes to a value less
		than the current value, entries are deleted
		from the media-specific table associated with this
		snL4VirtualServerHistoryControlEntry.Enough of the oldest of these
		entries shall be deleted by the agent so that their
		number remains less than or equal to the new value of
		this object.
	
		When the value of this object changes to a value
		greater than the current value, the number of
		associated media- specific entries may be allowed to
		grow."
	::= { snL4VirtualServerHistoryControlEntry 4 }

snL4VirtualServerHistoryControlInterval OBJECT-TYPE
	SYNTAX INTEGER (1..3600)
	ACCESS read-write
	STATUS mandatory
	DESCRIPTION
		"The interval in seconds over which the data is
		sampled for each bucket in the part of the
		media-specific table associated with this
		snL4VirtualServerHistoryControlEntry.This interval can
		be set to any number of seconds between 1 and
		3600 (1 hour).
	
		Because the counters in a bucket may overflow at their
		maximum value with no indication, a prudent manager
		will take into account the possibility of overflow
		in any of the associated counters.It is important
		to consider the minimum time in which any counter
		could overflow on a particular media type and set
		the snL4VirtualServerHistoryControlInterval object to a value less
		than this interval.This is typically most
		important for the 'octets' counter in any
		media-specific table.	
		This object may not be modified if the associated
		snL4VirtualServerHistoryControlStatus object is equal to valid(1)."
	DEFVAL { 1800 }
	::= { snL4VirtualServerHistoryControlEntry 5 }

snL4VirtualServerHistoryControlOwner OBJECT-TYPE
	SYNTAX DisplayString
	ACCESS read-write
	STATUS mandatory
	DESCRIPTION
		"The entity that configured this entry and is
		therefore using the resources assigned to it."
	::= { snL4VirtualServerHistoryControlEntry 6 }

snL4VirtualServerHistoryControlStatus OBJECT-TYPE
	SYNTAX INTEGER { 
				valid(1),
             	createRequest(2),
             	underCreation(3),
             	invalid(4)
           }
	ACCESS read-write
	STATUS mandatory
	DESCRIPTION
		"The status of this snL4VirtualServerHistoryControl entry.
		Each instance of the media-specific table associated
		with this snL4VirtualServerHistoryControlEntry will be deleted by the
		agent if this snL4VirtualServerHistoryControlEntry is not equal to
		valid(1)."
	::= { snL4VirtualServerHistoryControlEntry 7 }


-- The Virtual Server History Group


snL4VirtualServerHistoryTable OBJECT-TYPE
	SYNTAX SEQUENCE OF SnL4VirtualServerHistoryEntry
	ACCESS not-accessible
	STATUS mandatory
	DESCRIPTION
		"A list of Ethernet snL4History entries."
	::= { snL4History 6 }

snL4VirtualServerHistoryEntry OBJECT-TYPE
	SYNTAX SnL4VirtualServerHistoryEntry
	ACCESS not-accessible
	STATUS mandatory
	DESCRIPTION
		"An historical sample of Ethernet statistics on a
		particular Ethernet interface.  This sample is
		associated with the snL4VirtualServerHistoryControlEntry which set up
		the parameters for a regular collection of these
		samples.  As an example, an instance of the
		snL4VirtualServerHistoryReceivePkts object might be named
		snL4VirtualServerHistoryReceivePkts.2.89"
	INDEX { snL4VirtualServerHistoryIndex , snL4VirtualServerHistorySampleIndex }
	::= { snL4VirtualServerHistoryTable 1 }

SnL4VirtualServerHistoryEntry ::= SEQUENCE {
	snL4VirtualServerHistoryIndex                 
		INTEGER (1..65535),
	snL4VirtualServerHistorySampleIndex           
		INTEGER (1..2147483647),
	snL4VirtualServerHistoryIntervalStart         
		TimeTicks,
	snL4VirtualServerHistoryReceivePkts
		Counter,
	snL4VirtualServerHistoryTransmitPkts
		Counter,
	snL4VirtualServerHistoryTotalConnections
		Counter,
	snL4VirtualServerHistoryCurConnections
		INTEGER,
	snL4VirtualServerHistoryPeakConnections
		INTEGER
    }

snL4VirtualServerHistoryIndex OBJECT-TYPE
	SYNTAX INTEGER (1..65535)
	ACCESS read-only
	STATUS mandatory
	DESCRIPTION
		"The snL4VirtualServerHistory of which this entry is a part.The
		snL4VirtualServerHistory identified by a particular value of this
		index is the same snL4VirtualServerHistory as identified
		by the same value of snL4VirtualServerHistoryControlIndex."
	::= { snL4VirtualServerHistoryEntry 1 }

snL4VirtualServerHistorySampleIndex OBJECT-TYPE
	SYNTAX INTEGER (1..2147483647)
	ACCESS read-only
	STATUS mandatory
	DESCRIPTION
		"An index that uniquely identifies the particular
		sample this entry represents among all samples
		associated with the same snL4VirtualServerHistoryControlEntry.
		This index starts at 1 and increases by one
		as each new sample is taken."
	::= { snL4VirtualServerHistoryEntry 2 }

snL4VirtualServerHistoryIntervalStart OBJECT-TYPE
	SYNTAX TimeTicks
	ACCESS read-only
	STATUS mandatory
	DESCRIPTION
		"The value of sysUpTime at the start of the interval
		over which this sample was measured.If the probe
		keeps track of the time of day, it should start
		the first sample of the snL4VirtualServerHistory at a time such that
		when the next hour of the day begins, a sample is
		started at that instant.Note that following this
		rule may require the probe to delay collecting the
		first sample of the snL4VirtualServerHistory, as each sample must be
		of the same interval.Also note that the sample which
		is currently being collected is not accessible in this
		table until the end of its interval."
	::= { snL4VirtualServerHistoryEntry 3 }


snL4VirtualServerHistoryReceivePkts	  OBJECT-TYPE
	SYNTAX	Counter
	ACCESS  read-only
	STATUS  mandatory
	DESCRIPTION
		""
	::= { snL4VirtualServerHistoryEntry 4 }

snL4VirtualServerHistoryTransmitPkts  OBJECT-TYPE
	SYNTAX	Counter
	ACCESS  read-only
	STATUS  mandatory
	DESCRIPTION
		""
	::= { snL4VirtualServerHistoryEntry 5 }

snL4VirtualServerHistoryTotalConnections   OBJECT-TYPE
	SYNTAX	Counter
	ACCESS  read-only
	STATUS  mandatory
	DESCRIPTION
		""
	::= { snL4VirtualServerHistoryEntry 6 }

snL4VirtualServerHistoryCurConnections   OBJECT-TYPE
	SYNTAX	INTEGER
	ACCESS  read-only
	STATUS  mandatory
	DESCRIPTION
		""
	::= { snL4VirtualServerHistoryEntry 7 }

snL4VirtualServerHistoryPeakConnections   OBJECT-TYPE
	SYNTAX	INTEGER
	ACCESS  read-only
	STATUS  mandatory
	DESCRIPTION
		""
	::= { snL4VirtualServerHistoryEntry 8 }


-- Virtual Server Port Monitor Group

-- The Virtual Server Port History Control Group


snL4VirtualServerPortHistoryControlTable OBJECT-TYPE
	SYNTAX SEQUENCE OF SnL4VirtualServerPortHistoryControlEntry
	ACCESS not-accessible
	STATUS mandatory
	DESCRIPTION
		"A list of history control entries."
	::= { snL4History 7 }

snL4VirtualServerPortHistoryControlEntry OBJECT-TYPE
	SYNTAX SnL4VirtualServerPortHistoryControlEntry
	ACCESS not-accessible
	STATUS mandatory
	DESCRIPTION
		"A list of parameters that set up a periodic sampling
		of statistics.As an example, an instance of the
		snL4VirtualServerPortHistoryControlInterval object might be named
		snL4VirtualServerPortHistoryControlInterval.2"
	INDEX { snL4VirtualServerPortHistoryControlIndex }
	::= { snL4VirtualServerPortHistoryControlTable 1 }

	SnL4VirtualServerPortHistoryControlEntry ::= SEQUENCE {
		snL4VirtualServerPortHistoryControlIndex			 
			INTEGER (1..65535),
		snL4VirtualServerPortHistoryControlDataSource		
			OBJECT IDENTIFIER,
		snL4VirtualServerPortHistoryControlBucketsRequested
			INTEGER (1..65535),
		snL4VirtualServerPortHistoryControlBucketsGranted	
			INTEGER (1..65535),
		snL4VirtualServerPortHistoryControlInterval		
			INTEGER (1..3600),
		snL4VirtualServerPortHistoryControlOwner			 
			DisplayString,
		snL4VirtualServerPortHistoryControlStatus			
			INTEGER
	}

snL4VirtualServerPortHistoryControlIndex OBJECT-TYPE
	SYNTAX INTEGER (1..65535)
	ACCESS read-only
	STATUS mandatory
	DESCRIPTION
		"An index that uniquely identifies an entry in the
		snL4VirtualServerPortHistoryControl table.Each such entry defines a
		set of samples at a particular interval for an
		interface on the device."
	::= { snL4VirtualServerPortHistoryControlEntry 1 }

snL4VirtualServerPortHistoryControlDataSource OBJECT-TYPE
	SYNTAX OBJECT IDENTIFIER
	ACCESS read-write
	STATUS mandatory
	DESCRIPTION
		"This object identifies the source of the data for
		which historical data was collected and
		placed in a media-specific table on behalf of this
		snL4VirtualServerPortHistoryControlEntry.This source can be any
		real/virtual server and real/virtual server port on 
		this ServerIron.  In order to identify
		a particular instance, this object shall identify
		the instance of the object, defined in the above 
		statistics tables.
	
		This object may not be modified if the associated
		snL4VirtualServerPortHistoryControlStatus object is equal to valid(1)."
	::= { snL4VirtualServerPortHistoryControlEntry 2 }

snL4VirtualServerPortHistoryControlBucketsRequested OBJECT-TYPE
	SYNTAX INTEGER (1..65535)
	ACCESS read-write
	STATUS mandatory
	DESCRIPTION
		"The requested number of discrete time intervals
		over which data is to be saved in the part of the
		media-specific table associated with this
		snL4VirtualServerPortHistoryControlEntry.
	
		When this object is created or modified, the probe
		should set snL4VirtualServerPortHistoryControlBucketsGranted as closely to
		this object as is possible for the particular probe
		implementation and available resources."
	DEFVAL { 50 }
	::= { snL4VirtualServerPortHistoryControlEntry 3 }

snL4VirtualServerPortHistoryControlBucketsGranted OBJECT-TYPE
	SYNTAX INTEGER (1..65535)
	ACCESS read-only
	STATUS mandatory
	DESCRIPTION
		"The number of discrete sampling intervals
		over which data shall be saved in the part of
		the media-specific table associated with this
		snL4VirtualServerPortHistoryControlEntry.
	
		When the associated snL4VirtualServerPortHistoryControlBucketsRequested
		object is created or modified, the probe
		should set this object as closely to the requested
		value as is possible for the particular
		probe implementation and available resources.The
		probe must not lower this value except as a result
		of a modification to the associated
		snL4VirtualServerPortHistoryControlBucketsRequested object.
	
		There will be times when the actual number of
		buckets associated with this entry is less than
		the value of this object.In this case, at the
		end of each sampling interval, a new bucket will
		be added to the media-specific table.
	
		When the number of buckets reaches the value of
		this object and a new bucket is to be added to the
		media-specific table, the oldest bucket associated
		with this snL4VirtualServerPortHistoryControlEntry shall be deleted by
		the agent so that the new bucket can be added.
	
		When the value of this object changes to a value less
		than the current value, entries are deleted
		from the media-specific table associated with this
		snL4VirtualServerPortHistoryControlEntry.Enough of the oldest of these
		entries shall be deleted by the agent so that their
		number remains less than or equal to the new value of
		this object.
	
		When the value of this object changes to a value
		greater than the current value, the number of
		associated media- specific entries may be allowed to
		grow."
	::= { snL4VirtualServerPortHistoryControlEntry 4 }

snL4VirtualServerPortHistoryControlInterval OBJECT-TYPE
	SYNTAX INTEGER (1..3600)
	ACCESS read-write
	STATUS mandatory
	DESCRIPTION
		"The interval in seconds over which the data is
		sampled for each bucket in the part of the
		media-specific table associated with this
		snL4VirtualServerPortHistoryControlEntry.This interval can
		be set to any number of seconds between 1 and
		3600 (1 hour).
	
		Because the counters in a bucket may overflow at their
		maximum value with no indication, a prudent manager
		will take into account the possibility of overflow
		in any of the associated counters.It is important
		to consider the minimum time in which any counter
		could overflow on a particular media type and set
		the snL4VirtualServerPortHistoryControlInterval object to a value less
		than this interval.This is typically most
		important for the 'octets' counter in any
		media-specific table.	
		This object may not be modified if the associated
		snL4VirtualServerPortHistoryControlStatus object is equal to valid(1)."
	DEFVAL { 1800 }
	::= { snL4VirtualServerPortHistoryControlEntry 5 }

snL4VirtualServerPortHistoryControlOwner OBJECT-TYPE
	SYNTAX DisplayString
	ACCESS read-write
	STATUS mandatory
	DESCRIPTION
		"The entity that configured this entry and is
		therefore using the resources assigned to it."
	::= { snL4VirtualServerPortHistoryControlEntry 6 }

snL4VirtualServerPortHistoryControlStatus OBJECT-TYPE
	SYNTAX INTEGER { 
				valid(1),
             	createRequest(2),
             	underCreation(3),
             	invalid(4)
           }
	ACCESS read-write
	STATUS mandatory
	DESCRIPTION
		"The status of this snL4VirtualServerPortHistoryControl entry.
		Each instance of the media-specific table associated
		with this snL4VirtualServerPortHistoryControlEntry will be deleted by the
		agent if this snL4VirtualServerPortHistoryControlEntry is not equal to
		valid(1)."
	::= { snL4VirtualServerPortHistoryControlEntry 7 }


-- The Virtual Server Port History Group


snL4VirtualServerPortHistoryTable OBJECT-TYPE
	SYNTAX SEQUENCE OF SnL4VirtualServerPortHistoryEntry
	ACCESS not-accessible
	STATUS mandatory
	DESCRIPTION
		"A list of Ethernet snL4History entries."
	::= { snL4History 8 }

snL4VirtualServerPortHistoryEntry OBJECT-TYPE
	SYNTAX SnL4VirtualServerPortHistoryEntry
	ACCESS not-accessible
	STATUS mandatory
	DESCRIPTION
		"An historical sample of Ethernet statistics on a
		particular Ethernet interface.  This sample is
		associated with the snL4VirtualServerPortHistoryControlEntry which set up
		the parameters for a regular collection of these
		samples.  As an example, an instance of the
		snL4VirtualServerPortHistoryReceivePkts object might be named
		snL4VirtualServerPortHistoryReceivePkts.2.89"
	INDEX { snL4VirtualServerPortHistoryIndex , snL4VirtualServerPortHistorySampleIndex }
	::= { snL4VirtualServerPortHistoryTable 1 }

SnL4VirtualServerPortHistoryEntry ::= SEQUENCE {
	snL4VirtualServerPortHistoryIndex                 
		INTEGER (1..65535),
	snL4VirtualServerPortHistorySampleIndex           
		INTEGER (1..2147483647),
	snL4VirtualServerPortHistoryIntervalStart         
		TimeTicks,
	snL4VirtualServerPortHistoryReceivePkts
		Counter,
	snL4VirtualServerPortHistoryTransmitPkts
		Counter,
	snL4VirtualServerPortHistoryTotalConnections
		Counter,
	snL4VirtualServerPortHistoryCurConnections
		INTEGER,
	snL4VirtualServerPortHistoryPeakConnections
		INTEGER
    }

snL4VirtualServerPortHistoryIndex OBJECT-TYPE
	SYNTAX INTEGER (1..65535)
	ACCESS read-only
	STATUS mandatory
	DESCRIPTION
		"The snL4VirtualServerPortHistory of which this entry is a part.The
		snL4VirtualServerPortHistory identified by a particular value of this
		index is the same snL4VirtualServerPortHistory as identified
		by the same value of snL4VirtualServerPortHistoryControlIndex."
	::= { snL4VirtualServerPortHistoryEntry 1 }

snL4VirtualServerPortHistorySampleIndex OBJECT-TYPE
	SYNTAX INTEGER (1..2147483647)
	ACCESS read-only
	STATUS mandatory
	DESCRIPTION
		"An index that uniquely identifies the particular
		sample this entry represents among all samples
		associated with the same snL4VirtualServerPortHistoryControlEntry.
		This index starts at 1 and increases by one
		as each new sample is taken."
	::= { snL4VirtualServerPortHistoryEntry 2 }

snL4VirtualServerPortHistoryIntervalStart OBJECT-TYPE
	SYNTAX TimeTicks
	ACCESS read-only
	STATUS mandatory
	DESCRIPTION
		"The value of sysUpTime at the start of the interval
		over which this sample was measured.If the probe
		keeps track of the time of day, it should start
		the first sample of the snL4VirtualServerPortHistory at a time such that
		when the next hour of the day begins, a sample is
		started at that instant.Note that following this
		rule may require the probe to delay collecting the
		first sample of the snL4VirtualServerPortHistory, as each sample must be
		of the same interval.Also note that the sample which
		is currently being collected is not accessible in this
		table until the end of its interval."
	::= { snL4VirtualServerPortHistoryEntry 3 }


snL4VirtualServerPortHistoryReceivePkts	  OBJECT-TYPE
	SYNTAX	Counter
	ACCESS  read-only
	STATUS  mandatory
	DESCRIPTION
		""
	::= { snL4VirtualServerPortHistoryEntry 4 }

snL4VirtualServerPortHistoryTransmitPkts  OBJECT-TYPE
	SYNTAX	Counter
	ACCESS  read-only
	STATUS  mandatory
	DESCRIPTION
		""
	::= { snL4VirtualServerPortHistoryEntry 5 }

snL4VirtualServerPortHistoryTotalConnections   OBJECT-TYPE
	SYNTAX	Counter
	ACCESS  read-only
	STATUS  mandatory
	DESCRIPTION
		""
	::= { snL4VirtualServerPortHistoryEntry 6 }

snL4VirtualServerPortHistoryCurConnections   OBJECT-TYPE
	SYNTAX	INTEGER
	ACCESS  read-only
	STATUS  mandatory
	DESCRIPTION
		""
	::= { snL4VirtualServerPortHistoryEntry 7 }

snL4VirtualServerPortHistoryPeakConnections   OBJECT-TYPE
	SYNTAX	INTEGER
	ACCESS  read-only
	STATUS  mandatory
	DESCRIPTION
		""
	::= { snL4VirtualServerPortHistoryEntry 8 }

END
FOUNDRY-SN-POS-GROUP-MIB DEFINITIONS ::= BEGIN


-- Foundry POS Group MIB Release 1.0.0
-- Revision 0 10/28/99

-- Copyright 1996-1999 Foundry Networks, Inc.
-- All rights reserved.
-- This Foundry Networks SNMP Management Information Base Specification
-- (Specification) embodies Foundry Networks' confidential and
-- proprietary intellectual property. Foundry Networks retains all
-- title and ownership in the Specification, including any
-- revisions.

-- This Specification is supplied "AS IS," and Foundry Networks makes
-- no warranty, either express or implied, as to the use,
-- operation, condition, or performance of the Specification.

-- SECTION 1: Top Level Definitions


-- Imports

IMPORTS
	Counter, Gauge
		FROM RFC1155-SMI
	OBJECT-TYPE             
		FROM RFC-1212
	snPOS
		FROM FOUNDRY-SN-ROOT-MIB;

	-- textual conventions
	-- maximum of ports are 32.  

	--  Status Values

	    POSStatus ::= INTEGER { disabled(0), enabled(1) }

	  DisplayString ::=
	      OCTET STRING
	  -- This data type is used to model textual information taken
	  -- from the NVT ASCII character set.  By convention, objects
	  -- with this syntax are declared as having
	  --
	  --      SIZE (0..255)
    

snPOSInfo						OBJECT IDENTIFIER	  ::= { snPOS 1  }

-- POS Port table information

snPOSInfoTable OBJECT-TYPE
	SYNTAX  SEQUENCE OF SnPOSInfoEntry
	ACCESS  not-accessible
	STATUS  mandatory
	DESCRIPTION
		"A specific snPOSInfo group consists of a number of 
		 switch ports.  "
	::= { snPOSInfo 1 }

snPOSInfoEntry OBJECT-TYPE
	SYNTAX  SnPOSInfoEntry
	ACCESS  not-accessible
	STATUS  mandatory
	DESCRIPTION
		"An entry in the snPOSInfo table indicates the 
		 configuration on a specified port. A SNMP SET PDU 
		 for a row of the snPOSInfoTable requires the entired 
		 sequence of the MIB Objects in each 
		 snPOSInfoEntry stored in one PDU.  Otherwise, 
	 	 GENERR return-value will be returned."
	INDEX   { 
		snPOSInfoPortNum
	}
	::= { snPOSInfoTable 1 }

SnPOSInfoEntry ::= SEQUENCE {
	snPOSInfoPortNum
		INTEGER,
	snPOSIfIndex
	    INTEGER,
	snPOSDescr
	    DisplayString,
	snPOSName
		DisplayString,
	snPOSInfoSpeed
	    INTEGER,
	snPOSInfoAdminStatus
		INTEGER,
	snPOSInfoLinkStatus
		INTEGER,
	snPOSInfoClock
	    INTEGER,
	snPOSInfoLoopBack
	    INTEGER,
	snPOSInfoScrambleATM 
	    POSStatus,
	snPOSInfoFraming 
	    INTEGER,
	snPOSInfoCRC 
	    INTEGER,
	snPOSInfoKeepAlive 
	    INTEGER,
	snPOSInfoFlagC2 
	    INTEGER,
	snPOSInfoFlagJ0 
	    INTEGER,
	snPOSInfoFlagH1 
	    INTEGER,
    snPOSStatsInFrames 
    	Counter,
	snPOSStatsOutFrames 
    	Counter,
	snPOSStatsAlignErrors            
		Counter,
    snPOSStatsFCSErrors                  
		Counter,
    snPOSStatsFrameTooLongs              
		Counter,
	snPOSStatsFrameTooShorts
	    Counter,
	snPOSStatsInDiscard
	    Counter,
	snPOSStatsOutDiscard
	    Counter,
	snPOSInOctets
	    OCTET STRING,
	snPOSOutOctets
	    OCTET STRING,
	snPOSStatsInBitsPerSec
	    Gauge,
	snPOSStatsOutBitsPerSec
	    Gauge,
	snPOSStatsInPktsPerSec
	    Gauge,
	snPOSStatsOutPktsPerSec
	    Gauge,
	snPOSStatsInUtilization
	    INTEGER (0..10000),
	snPOSStatsOutUtilization
	    INTEGER (0..10000),
	snPOSTagType
	    INTEGER  
	}


snPOSInfoPortNum OBJECT-TYPE
	SYNTAX  INTEGER
	ACCESS  read-only
	STATUS  mandatory
	DESCRIPTION
		"The port index.
		 The bit 0 to bit 7: port number. 
		 The bit 8 to bit 11: slot number (slot for chassis only)."
	::= { snPOSInfoEntry 1 }


snPOSIfIndex OBJECT-TYPE
    SYNTAX  INTEGER
    ACCESS  read-only
    STATUS  mandatory
    DESCRIPTION
    	"In order to identify a particular interface, this
		object shall identify the instance of the ifIndex
		object, defined in RFC 1213 and RFC 1573."
    ::= { snPOSInfoEntry 2 }


snPOSDescr OBJECT-TYPE
    SYNTAX  DisplayString
    ACCESS  read-only
    STATUS  mandatory
    DESCRIPTION
    	"A textual string containing the slot/port information
    	about the interface."
    ::= { snPOSInfoEntry 3 }


snPOSName OBJECT-TYPE
	SYNTAX	DisplayString (SIZE(0..255))
	ACCESS	read-write
	STATUS	mandatory
	DESCRIPTION
		"Port Name string."
	::= { snPOSInfoEntry 4 }

snPOSInfoSpeed OBJECT-TYPE
	SYNTAX  INTEGER {
		s155000(1),
		s622000(2),
		other(3),
		s2488000(4)
		}
	ACCESS  read-write
	STATUS  mandatory
	DESCRIPTION     
		"The speed configuration for a port. The values are:
		155000
		622000
		2488000
		"
	::= { snPOSInfoEntry 5 }


snPOSInfoAdminStatus OBJECT-TYPE
    SYNTAX  INTEGER {
		up(1),       -- ready to pass packets
		down(2),
		testing(3)   -- in some test mode
		}
    ACCESS  read-write
    STATUS  mandatory
    DESCRIPTION
		"The desired state of all ports.  The
	 	testing(3) state indicates that no operational
	 	packets can be passed. 
	 	(same as ifAdminStatus in MIB-II)"
    ::= { snPOSInfoEntry 6 }


snPOSInfoLinkStatus OBJECT-TYPE
    SYNTAX  INTEGER {
    	up(1),       -- ready to pass packets
    	down(2),
    	testing(3)   -- in some test mode
        }
    ACCESS  read-only
    STATUS  mandatory
    DESCRIPTION
        "The current operational state of the interface.
         The testing(3) state indicates that no operational
         packets can be passed. 
         (same as ifOperStatus in MIB-II)"
    ::= { snPOSInfoEntry 7 }


snPOSInfoClock  OBJECT-TYPE
    SYNTAX  INTEGER {
    	internal(1),     
    	line(2)
        }
    ACCESS  read-write
    STATUS  mandatory
    DESCRIPTION
		"Clock default internal"
    ::= { snPOSInfoEntry 8 }

snPOSInfoLoopBack   OBJECT-TYPE
    SYNTAX  INTEGER {
    	line(1),     
    	internal(2),
    	none(3)
        }
    ACCESS  read-write
    STATUS  mandatory
    DESCRIPTION
		"Loop back default none"
    ::= { snPOSInfoEntry 9 }

snPOSInfoScrambleATM  OBJECT-TYPE
	SYNTAX	POSStatus
    ACCESS  read-write
    STATUS  mandatory
    DESCRIPTION
		"ATM style scrambling default off"
    ::= { snPOSInfoEntry 10 }

snPOSInfoFraming  OBJECT-TYPE
    SYNTAX  INTEGER {
    	sonet(1),     
    	sdh(2)
        }
    ACCESS  read-write
    STATUS  mandatory
    DESCRIPTION
		"Framing default SONET"
    ::= { snPOSInfoEntry 11 }

snPOSInfoCRC  OBJECT-TYPE
    SYNTAX  INTEGER {
    	crc32bits(1),     
    	crc16bits(2)
        }
    ACCESS  read-write
    STATUS  mandatory
    DESCRIPTION
		"CRC default 32 bit"
    ::= { snPOSInfoEntry 12 }

snPOSInfoKeepAlive  OBJECT-TYPE
	SYNTAX  INTEGER (0..32767)
    ACCESS  read-write
    STATUS  mandatory
    DESCRIPTION
		"Keep-alive default 10"
    ::= { snPOSInfoEntry 13 }

snPOSInfoFlagC2  OBJECT-TYPE
	SYNTAX  INTEGER (0..255)
    ACCESS  read-write
    STATUS  mandatory
    DESCRIPTION
		"C2 flag"
    ::= { snPOSInfoEntry 14 }


snPOSInfoFlagJ0  OBJECT-TYPE
	SYNTAX  INTEGER (0..255)
    ACCESS  read-write
    STATUS  mandatory
    DESCRIPTION
		"J0 flag"
    ::= { snPOSInfoEntry 15 }

snPOSInfoFlagH1  OBJECT-TYPE
	SYNTAX  INTEGER (0..255)
    ACCESS  read-write
    STATUS  mandatory
    DESCRIPTION
		"H1 flag"
    ::= { snPOSInfoEntry 16 }

snPOSStatsInFrames OBJECT-TYPE
    SYNTAX  Counter
    ACCESS  read-only
    STATUS  mandatory
    DESCRIPTION
    	"The total number of packets received on the interface."
    ::= { snPOSInfoEntry 17 }


snPOSStatsOutFrames OBJECT-TYPE
    SYNTAX  Counter
    ACCESS  read-only
    STATUS  mandatory
    DESCRIPTION
    	"The total number of packets transmitted out of the interface."
    ::= { snPOSInfoEntry 18 }


snPOSStatsAlignErrors   OBJECT-TYPE
     SYNTAX     Counter
     ACCESS     read-only
     STATUS     mandatory
     DESCRIPTION
	 	"dot3StatsAlignmentErrors : A count of frames 
	  	received on a particular interface that are 
	  	not an integral number of octets in length 
	  	and do not pass the FCS check.

	  	The count represented by an instance of this
	  	object is incremented when the alignmentError
	  	status is returned by the MAC service to the
	  	LLC (or other MAC user). Received frames for
	  	which multiple error conditions obtain are,
	  	according to the conventions of IEEE 802.3
	  	Layer Management, counted exclusively according
	  	to the error status presented to the LLC."
    ::= { snPOSInfoEntry 19 }

snPOSStatsFCSErrors   OBJECT-TYPE
     SYNTAX      Counter
     ACCESS      read-only
     STATUS      mandatory
     DESCRIPTION
	 	"dot3StatsFCSErrors : A count of frames received 
	  	on a particular interface that are an integral 
	  	number of octets in length but do not pass the 
	  	FCS check.

	  	The count represented by an instance of this
	  	object is incremented when the frameCheckError
	  	status is returned by the MAC service to the
	  	LLC (or other MAC user). Received frames for
	  	which multiple error conditions obtain are,
	  	according to the conventions of IEEE 802.3
	  	Layer Management, counted exclusively according
	  	to the error status presented to the LLC."
    ::= { snPOSInfoEntry 20 }


snPOSStatsFrameTooLongs   OBJECT-TYPE
     SYNTAX    Counter
     ACCESS    read-only
     STATUS    mandatory
     DESCRIPTION
	 	"dot3StatsFrameTooLongs : A count of frames 
	  	received on a particular interface that 
	  	exceed the maximum permitted frame size.

	  	The count represented by an instance of this
	  	object is incremented when the frameTooLong
	  	status is returned by the MAC service to the
	  	LLC (or other MAC user). Received frames for
	  	which multiple error conditions obtain are,
	  	according to the conventions of IEEE 802.3
	  	Layer Management, counted exclusively according
	  	to the error status presented to the LLC."
    ::= { snPOSInfoEntry 21 }


snPOSStatsFrameTooShorts   OBJECT-TYPE
     SYNTAX    Counter
     ACCESS    read-only
     STATUS    mandatory
     DESCRIPTION
	 	" A count of frames received on a particular 
	 	interface that below the minimum permitted 
	 	frame size."
    ::= { snPOSInfoEntry 22 }

snPOSStatsInDiscard OBJECT-TYPE
    SYNTAX  Counter
    ACCESS  read-only
    STATUS  mandatory
    DESCRIPTION
        "The number of inbound packets which were chosen
         to be discarded even though no errors had been
         detected to prevent their being deliverable to a
         higher-layer protocol.  One possible reason for
         discarding such a packet could be to free up
         buffer space."
    ::= { snPOSInfoEntry 23 }


snPOSStatsOutDiscard OBJECT-TYPE
    SYNTAX  Counter
    ACCESS  read-only
    STATUS  mandatory
    DESCRIPTION
        "The number of outbound packets which were chosen
         to be discarded even though no errors had been
         detected to prevent their being transmitted.  One
         possible reason for discarding such a packet could
         be to free up buffer space."
    ::= { snPOSInfoEntry 24 }

snPOSInOctets OBJECT-TYPE
    SYNTAX  OCTET STRING (SIZE(8))
    ACCESS  read-only
    STATUS  mandatory
    DESCRIPTION
    	"The total number of octets received on the interface,
    	including framing characters. This object is a 64-bit
		counter of the ifInOctets object, defined in RFC 1213.
		The octet string is in big-endian byte order."
    ::= { snPOSInfoEntry 25 }


snPOSOutOctets OBJECT-TYPE
    SYNTAX  OCTET STRING (SIZE(8))
    ACCESS  read-only
    STATUS  mandatory
    DESCRIPTION
    	"The total number of octets transmitted out of the interface,
    	including framing characters. This object is a 64-bit
		counter of the ifOutOctets object, defined in RFC 1213.
		The octet string is in big-endian byte order."
    ::= { snPOSInfoEntry 26 }


snPOSStatsInBitsPerSec OBJECT-TYPE
    SYNTAX  Gauge
    ACCESS  read-only
    STATUS  mandatory
    DESCRIPTION
    	"The number of bits per second received on the interface
    	over a 5 minutes interval."
    ::= { snPOSInfoEntry 27 }


snPOSStatsOutBitsPerSec OBJECT-TYPE
    SYNTAX  Gauge
    ACCESS  read-only
    STATUS  mandatory
    DESCRIPTION
    	"The number of bits per second transmitted out of the interface
    	over a 5 minutes interval."
    ::= { snPOSInfoEntry 28 }


snPOSStatsInPktsPerSec OBJECT-TYPE
    SYNTAX  Gauge
    ACCESS  read-only
    STATUS  mandatory
    DESCRIPTION
    	"The number of packets per second received on the interface
    	over a 5 minutes interval."
    ::= { snPOSInfoEntry 29 }


snPOSStatsOutPktsPerSec OBJECT-TYPE
    SYNTAX  Gauge
    ACCESS  read-only
    STATUS  mandatory
    DESCRIPTION
    	"The number of packets per second transmitted out of the interface
    	over a 5 minutes interval."
    ::= { snPOSInfoEntry 30 }


snPOSStatsInUtilization OBJECT-TYPE
    SYNTAX  INTEGER (0..10000)
    ACCESS  read-only
    STATUS  mandatory
    DESCRIPTION
    	"The input network utilization in hundredths of a percent
    	over a 5 minutes interval."
    ::= { snPOSInfoEntry 31 }


snPOSStatsOutUtilization OBJECT-TYPE
    SYNTAX  INTEGER (0..10000)
    ACCESS  read-only
    STATUS  mandatory
    DESCRIPTION
    	"The output network utilization in hundredths of a percent
    	over a 5 minutes interval."
    ::= { snPOSInfoEntry 32 }

snPOSTagType OBJECT-TYPE
	SYNTAX  INTEGER {
		tagged(1),      
		untagged(2)    
		}
	ACCESS  read-only
	STATUS  mandatory
	DESCRIPTION
		"For tagged port, we could have multiple VLANs 
		 per port."  
	::= {snPOSInfoEntry  33}

END
FOUNDRY-SN-IGMP-MIB DEFINITIONS ::= BEGIN


-- Foundry IGMP Group MIB Release 1.0.0
-- Revision 0 2/13/98

-- Copyright 1996-98 Foundry Networks, Inc.
-- All rights reserved.
-- This Foundry Networks SNMP Management Information Base 
-- Specification embodies Foundry Networks' confidential and
-- proprietary intellectual property. Foundry Networks retains all
-- title and ownership in the Specification, including any
-- revisions.

-- This Specification is supplied "AS IS," and Foundry Networks makes
-- no warranty, either express or implied, as to the use,
-- operation, condition, or performance of the Specification.

-- SECTION 1: Top Level Definitions


-- Imports

IMPORTS
	IpAddress
		FROM RFC1155-SMI
	OBJECT-TYPE
		FROM RFC-1212
	snIgmp
		FROM FOUNDRY-SN-ROOT-MIB;


-- SECTION 2: MIB 

-- IGMP MIB

snIgmpMIBObjects OBJECT IDENTIFIER ::= { snIgmp 1 }

snIgmpQueryInterval OBJECT-TYPE
    SYNTAX     INTEGER (0..3600)
    ACCESS     read-write
    STATUS     mandatory
    DESCRIPTION
            "This is the time interval at which this entity sends out
			IGMP host query packets. For a router, snDvmrpEnable must
			have been set to 'enabled' before this object is writen.
			For a switch, snSwGroupIpMcastMode must have been set to
			'enabled' and snSwIpMcastQuerierMode must have been set
			to 'querier' before this object is writen.
			Value 0 cannot be used for SET operations. This value
			is returned if IGMP is not configured within the system."
    DEFVAL     { 60 }
    ::= { snIgmpMIBObjects 1 }

snIgmpGroupMembershipTime OBJECT-TYPE
    SYNTAX     INTEGER (0..7200)
    ACCESS     read-write
    STATUS     mandatory
    DESCRIPTION
            "This is the time interval after which a group is considered
            inactive. For a router, snDvmrpEnable must have been set to
            'enabled' before this object is writen. For a switch,
            snSwGroupIpMcastMode must have been set to 'enabled' before
            this object is writen.
            Value 0 cannot be used for SET operations. This value
            is returned if IGMP is not configured within the system."
    DEFVAL     { 140 }
    ::= { snIgmpMIBObjects 2 }

-- The IGMP Interface Table

snIgmpIfTable OBJECT-TYPE
    SYNTAX     SEQUENCE OF SnIgmpIfEntry
    ACCESS     not-accessible
    STATUS     mandatory
    DESCRIPTION
            "This table comprises of a list of IGMP interface entries."
    ::= { snIgmpMIBObjects 3 }

snIgmpIfEntry OBJECT-TYPE
    SYNTAX     SnIgmpIfEntry
    ACCESS     not-accessible
    STATUS     mandatory
    DESCRIPTION
            "An entry (conceptual row) contains the group
            membership information for that port."
    INDEX      { snIgmpIfEntryIndex }
    ::= { snIgmpIfTable 1 }

SnIgmpIfEntry ::= SEQUENCE {
    snIgmpIfEntryIndex         INTEGER,
    snIgmpIfPortNumber         INTEGER,
    snIgmpIfGroupAddress       IpAddress,
    snIgmpIfGroupAge           INTEGER }

snIgmpIfEntryIndex OBJECT-TYPE
    SYNTAX     INTEGER
    ACCESS     read-only
    STATUS     mandatory
    DESCRIPTION
            "The table entry index."
    ::= { snIgmpIfEntry 1 }

snIgmpIfPortNumber OBJECT-TYPE
    SYNTAX     INTEGER
    ACCESS     read-only
    STATUS     mandatory
    DESCRIPTION
            "This is the interface on which the group was learnt."
    ::= { snIgmpIfEntry 2 }

snIgmpIfGroupAddress OBJECT-TYPE
    SYNTAX     IpAddress
    ACCESS     read-only
    STATUS     mandatory
    DESCRIPTION
            "The group address learnt from the interface."
    ::= { snIgmpIfEntry 3 }

snIgmpIfGroupAge OBJECT-TYPE
    SYNTAX     INTEGER
    ACCESS     read-only
    STATUS     mandatory
    DESCRIPTION
            "This is the interval (seconds) after which the group
            information will be aged out."
    ::= { snIgmpIfEntry 4 }

END
-- *****************************************************************
-- Commited Access Rate MIB file.
-- *****************************************************************
FOUNDRY-CAR-MIB DEFINITIONS ::= BEGIN

IMPORTS
	OBJECT-TYPE,
	Gauge
		FROM RFC1155-SMI

        Counter64
		FROM SNMPv2-SMI


	snCAR
		FROM FOUNDRY-SN-SWITCH-GROUP-MIB;
			

snPortCARs	OBJECT IDENTIFIER ::= { snCAR 1 }

PacketSource ::= INTEGER { 
		input(0), --for inbound traffic
		output(1) --for outbound traffic
	}

RateLimitType ::= INTEGER { 
		all(3), 		--	all traffic.                             
		quickAcc(2), 	--	traffic matches rate-limit's access list.
		standardAcc(1) 	--	traffic matches standard access list.    
	}

RateLimitAction ::= INTEGER {
		continue(1), 
		drop(2), 
		precedCont(3),
		precedXmit(4), 
		xmit(5) 
	}


snPortCARTable OBJECT-TYPE
	SYNTAX  SEQUENCE OF SnPortCAREntry
	ACCESS  not-accessible
        STATUS  mandatory
        DESCRIPTION
        "A table of rate limit configuration entries.
	Rate Limit is a method of traffic control.  It allows a set
	of rate limits to be configured and applied to packets flowing
	into/out of an interface to regulate network traffic."

        ::= { snPortCARs 1 }

snPortCAREntry OBJECT-TYPE
        SYNTAX SnPortCAREntry
        ACCESS  not-accessible
        STATUS  mandatory
        DESCRIPTION
        	"A collection of rate-limit configuration objects on this 
		interface."
        INDEX { snPortCARifIndex, snPortCARDirection, snPortCARRowIndex }
        ::= { snPortCARTable 1 }

SnPortCAREntry ::=
	SEQUENCE {
		snPortCARifIndex
						INTEGER,
		snPortCARDirection
               		PacketSource,
		snPortCARRowIndex
                        INTEGER,
		snPortCARType
                        RateLimitType,
		snPortCARAccIdx
                        INTEGER,
		snPortCARRate
                        INTEGER,
		snPortCARLimit
                        INTEGER,
		snPortCARExtLimit
                        INTEGER,
		snPortCARConformAction
       					RateLimitAction,
		snPortCARExceedAction
       					RateLimitAction,
		snPortCARStatSwitchedPkts
                        Counter64,
		snPortCARStatSwitchedBytes
                        Counter64,
		snPortCARStatFilteredPkts
                        Counter64,
		snPortCARStatFilteredBytes
                        Counter64,
		snPortCARStatCurBurst
       					Gauge
	}
snPortCARifIndex OBJECT-TYPE
    SYNTAX     INTEGER 
    ACCESS     read-only
    STATUS     mandatory
    DESCRIPTION
            "The ifIndex value for this rate limit entry."
    ::= { snPortCAREntry 1 }

snPortCARDirection OBJECT-TYPE
	SYNTAX  PacketSource
        ACCESS  read-only
        STATUS  mandatory
        DESCRIPTION
       		"The input or output transmission direction for the 
                Rate Limit object.
				input (0), --for inbound traffic
				output(1) --for outbound traffic "
        ::= { snPortCAREntry 2 }

snPortCARRowIndex OBJECT-TYPE
	SYNTAX  INTEGER (1..2147483647)
        ACCESS  read-only
        STATUS  mandatory
        DESCRIPTION
                "The table index for rate limit objects.
		It increases as the rate limit entries are added.
		Skips the number when a row is deleted."

        ::= { snPortCAREntry 3 }

snPortCARType OBJECT-TYPE
	SYNTAX  RateLimitType
        ACCESS  read-only
        STATUS  mandatory
        DESCRIPTION
		"The type of traffic rate-limited against."

	::= { snPortCAREntry 4 }

snPortCARAccIdx OBJECT-TYPE
	SYNTAX  INTEGER
        ACCESS  read-only
        STATUS  mandatory
        DESCRIPTION
		"The index to the access list if RateLimitType is either
		quickAcc or standardAcc."

	::= { snPortCAREntry 5 }

snPortCARRate OBJECT-TYPE
	SYNTAX  INTEGER
        ACCESS  read-only
        STATUS  mandatory
        DESCRIPTION
		"The comitted access rate. This determines the long term
		average transmission rate. Traffic that falls under this
		rate always conforms. This is average rate in bits per 
		second."

	::= { snPortCAREntry 6 }

snPortCARLimit OBJECT-TYPE
	SYNTAX  INTEGER
        ACCESS  read-only
        STATUS  mandatory
        DESCRIPTION
		"This is the normal burst size that determines how large traffic
		bursts can be before some traffic exceeds the rate limit. This
		specifies the number of bytes that are guaranteed to be transported
		by the network at the average rate under normal conditions during
		committed time interval. This normal burst size is in bytes."

	::= { snPortCAREntry 7 }

snPortCARExtLimit OBJECT-TYPE
	SYNTAX  INTEGER
	ACCESS  read-only
	STATUS  mandatory
	DESCRIPTION
		"This is the extended burst limit that determines how large traffic
		bursts can be before all the traffic exceeds the rate limit. This
		burst size is in bytes."

	::= { snPortCAREntry 8 }

snPortCARConformAction OBJECT-TYPE
	SYNTAX	RateLimitAction
	ACCESS  read-only
	STATUS	mandatory
	DESCRIPTION
		"Action to be taken when the traffic is within
		the Rate Limit.
		drop		drop the packet.
		xmit		transmit the packet.
		continue	continue to evaluate to the subsequent
					rate limits.
		precedXmit	rewrite the IP precedence and transmit
					the packet.
		precedCont	rewrite the IP precedence and allow it
					evaluated by subsequent rate limits."

	::= { snPortCAREntry 9 }

snPortCARExceedAction OBJECT-TYPE
	SYNTAX	RateLimitAction
	ACCESS  read-only
	STATUS	mandatory
	DESCRIPTION
		"Action to be taken when the traffic exceeds
		the Rate Limit.drop		
		drop the packet.
		xmit		transmit the packet.
		continue	continue to evaluate to the subsequent
					rate limits.
		precedXmit	rewrite the IP precedence and transmit
					the packet.
		precedCont	rewrite the IP precedence and allow it
					evaluated by subsequent rate limits."

	::= { snPortCAREntry 10 }

snPortCARStatSwitchedPkts OBJECT-TYPE
	SYNTAX  Counter64
	ACCESS  read-only
	STATUS  mandatory
	DESCRIPTION
		"The counter of packets permitted by this rate limit."

	::= { snPortCAREntry 11 }

snPortCARStatSwitchedBytes OBJECT-TYPE
	SYNTAX  Counter64
	ACCESS  read-only
	STATUS  mandatory
	DESCRIPTION
		"The counter of bytes permitted by this interface."

	::= { snPortCAREntry 12 }

snPortCARStatFilteredPkts OBJECT-TYPE
	SYNTAX  Counter64
	--UNITS	"packets"
	ACCESS  read-only
	STATUS  mandatory
	DESCRIPTION
		"The counter of packets which exceeded this rate limit."

	::= { snPortCAREntry 13 }

snPortCARStatFilteredBytes OBJECT-TYPE
	SYNTAX  Counter64
	ACCESS  read-only
	STATUS  mandatory
	DESCRIPTION
		"The counter of bytes which exceeded this rate limit."

	::= { snPortCAREntry 14 }

snPortCARStatCurBurst OBJECT-TYPE
	SYNTAX  Gauge
	ACCESS  read-only
	STATUS  mandatory
	DESCRIPTION
		"The current received burst size."
	::= { snPortCAREntry 15 }

-- end of snPortCARTable


END
-- *****************************************************************
-- Foundry Commited Access Rate MIB file.
-- *****************************************************************
FOUNDRY-VLAN-CAR-MIB DEFINITIONS ::= BEGIN

IMPORTS
	OBJECT-TYPE,
	Gauge
		FROM RFC1155-SMI

        Counter64
		FROM SNMPv2-SMI

        PacketSource, RateLimitType, RateLimitAction
		FROM FOUNDRY-CAR-MIB  

  	snVLanCAR
  		FROM FOUNDRY-SN-SWITCH-GROUP-MIB;
	


snVLanCARs	OBJECT IDENTIFIER ::= { snVLanCAR 1 }



snVLanCARTable OBJECT-TYPE
	SYNTAX  SEQUENCE OF SnVLanCAREntry
	ACCESS  not-accessible
        STATUS  mandatory
        DESCRIPTION
        "A table of rate limit configuration entries for a vlan.
	Rate Limit is a method of traffic control.  It allows a set
	of rate limits to be configured and applied to packets flowing
	into/out of an interface to regulate network traffic."

        ::= { snVLanCARs 1 }


snVLanCAREntry OBJECT-TYPE
        SYNTAX SnVLanCAREntry
        ACCESS  not-accessible
        STATUS  mandatory
        DESCRIPTION
        	"A collection of rate-limit configuration objects on this 
		vlan."
        INDEX { snVLanCARVLanId, snVLanCARDirection, snVLanCARRowIndex }
        ::= { snVLanCARTable 1 }

SnVLanCAREntry ::=
	SEQUENCE {
		snVLanCARDirection
               		PacketSource,
		snVLanCARVLanId
                        INTEGER,
		snVLanCARRowIndex
                        INTEGER,
		snVLanCARType
                        RateLimitType,
		snVLanCARAccIdx
                        INTEGER,
		snVLanCARRate
                        INTEGER,
		snVLanCARLimit
                        INTEGER,
		snVLanCARExtLimit
                        INTEGER,
		snVLanCARConformAction
			RateLimitAction,
		snVLanCARExceedAction
       			RateLimitAction,
		snVLanCARStatSwitchedPkts
                        Counter64,
		snVLanCARStatSwitchedBytes
                        Counter64,
		snVLanCARStatFilteredPkts
                        Counter64,
		snVLanCARStatFilteredBytes
                        Counter64,
		snVLanCARStatCurBurst
       			Gauge
	}

--need to refer to the vlan table
--index once it is changed to single
--vlan id as the row index

snVLanCARVLanId OBJECT-TYPE
	SYNTAX  INTEGER (1..4095)
	ACCESS  read-only
	STATUS  mandatory
	DESCRIPTION
		"The VLAN ID as one of the indices of this table .
		 Each VLAN ID can have a membership of multiple 
		 ports."
	::= { snVLanCAREntry 1 }

snVLanCARDirection OBJECT-TYPE
	SYNTAX  PacketSource
        ACCESS  read-only
        STATUS  mandatory
        DESCRIPTION
       		"The input or output transmission direction for the 
                Rate Limit object."
        ::= { snVLanCAREntry 2 }

snVLanCARRowIndex OBJECT-TYPE
	SYNTAX  INTEGER (1..2147483647)
        ACCESS  read-only
        STATUS  mandatory
        DESCRIPTION
                "The table index for rate limit objects.
		It increases as the rate limit entries are added.
		Skips the number when a row is deleted."

        ::= { snVLanCAREntry 3 }

snVLanCARType OBJECT-TYPE
	SYNTAX  RateLimitType
        ACCESS  read-only
        STATUS  mandatory
        DESCRIPTION
		"The type of traffic rate-limited against."

	::= { snVLanCAREntry 4 }

snVLanCARAccIdx OBJECT-TYPE
	SYNTAX  INTEGER
        ACCESS  read-only
        STATUS  mandatory
        DESCRIPTION
		"The index to the access list if RateLimitType is either
		quickAcc or standardAcc."

	::= { snVLanCAREntry 5 }

snVLanCARRate OBJECT-TYPE
	SYNTAX  INTEGER
        ACCESS  read-only
        STATUS  mandatory
        DESCRIPTION
		"The comitted access rate. This determines the long term
		average transmission rate. Traffic that falls under this
		rate always conforms. This is average rate in bits per 
		second."

	::= { snVLanCAREntry 6 }

snVLanCARLimit OBJECT-TYPE
	SYNTAX  INTEGER
        ACCESS  read-only
        STATUS  mandatory
        DESCRIPTION
		"This is the normal burst size that determines how large traffic
		bursts can be before some traffic exceeds the rate limit. This
		specifies the number of bytes that are guaranteed to be transported
		by the network at the average rate under normal conditions during
		committed time interval. This normal burst size is in bytes."

	::= { snVLanCAREntry 7 }

snVLanCARExtLimit OBJECT-TYPE
	SYNTAX  INTEGER
	ACCESS  read-only
	STATUS  mandatory
	DESCRIPTION
		"This is the extended burst limit that determines how large traffic
		bursts can be before all the traffic exceeds the rate limit. This
		burst size is in bytes. "

	::= { snVLanCAREntry 8 }

snVLanCARConformAction OBJECT-TYPE
	SYNTAX	RateLimitAction
	ACCESS  read-only
	STATUS	mandatory
	DESCRIPTION
		"Action to be taken when the traffic is within
		the Rate Limit.
		drop		drop the packet.
		xmit		transmit the packet.
		continue	continue to evaluate to the subsequent
					rate limits.
		precedXmit	rewrite the IP precedence and transmit
					the packet.
		precedCont	rewrite the IP precedence and allow it
					evaluated by subsequent rate limits."

	::= { snVLanCAREntry 9 }

snVLanCARExceedAction OBJECT-TYPE
	SYNTAX	RateLimitAction
	ACCESS  read-only
	STATUS	mandatory
	DESCRIPTION
		"Action to be taken when the traffic exceeds
		the Rate Limit.
   		drop		drop the packet.
		xmit		transmit the packet.
		continue	continue to evaluate to the subsequent
					rate limits.
		precedXmit	rewrite the IP precedence and transmit
					the packet.
		precedCont	rewrite the IP precedence and allow it
					evaluated by subsequent rate limits."

	::= { snVLanCAREntry 10 }

snVLanCARStatSwitchedPkts OBJECT-TYPE
	SYNTAX  Counter64
	ACCESS  read-only
	STATUS  mandatory
	DESCRIPTION
		"The counter of packets permitted by this rate limit."

	::= { snVLanCAREntry 11 }

snVLanCARStatSwitchedBytes OBJECT-TYPE
	SYNTAX  Counter64
	ACCESS  read-only
	STATUS  mandatory
	DESCRIPTION
		"The counter of bytes permitted by this interface."

	::= { snVLanCAREntry 12 }

snVLanCARStatFilteredPkts OBJECT-TYPE
	SYNTAX  Counter64
	--UNITS	"packets"
	ACCESS  read-only
	STATUS  mandatory
	DESCRIPTION
		"The counter of packets which exceeded this rate limit."

	::= { snVLanCAREntry 13 }

snVLanCARStatFilteredBytes OBJECT-TYPE
	SYNTAX  Counter64
	ACCESS  read-only
	STATUS  mandatory
	DESCRIPTION
		"The counter of bytes which exceeded this rate limit."

	::= { snVLanCAREntry 14 }

snVLanCARStatCurBurst OBJECT-TYPE
	SYNTAX  Gauge
	ACCESS  read-only
	STATUS  mandatory
	DESCRIPTION
		"The current received burst size."
	::= { snVLanCAREntry 15 }

-- end of snVLanCARTable


END
FOUNDRY-SN-IP-ACL-MIB DEFINITIONS ::= BEGIN

-- Imports

IMPORTS
	IpAddress		
		FROM RFC1155-SMI
	OBJECT-TYPE     
		FROM RFC-1212
	Counter64		
		FROM SNMPv2-SMI
	snIp			
		FROM FOUNDRY-SN-ROOT-MIB;

	--  textual conventions
		DisplayString ::= OCTET STRING

	--  RtrStatus Values
		RtrStatus ::= INTEGER { disabled(0), enabled (1) }

	--  Row Status
	    SnRowStatus ::= INTEGER { 
							    other(1),
							    valid(2),
							    delete(3),
							    create(4)
						      }

	--  Action 
		Action ::= INTEGER { deny(0), permit(1) }

    --  Boolean Values
         TruthVal ::= INTEGER { false (0), true (1)  }

	--  ACL number
		AclNumber ::= INTEGER (1..199)

	--  Operator
		Operator ::= INTEGER { eq(0), neq(1), lt(2), gt(3), range(4), undefined(7) }

	--  IP Protocol
		IpProtocol ::= INTEGER (0..255)

	-- Precedence Value
		PrecedenceValue ::= INTEGER { critical(5), flash(3), flashoverride(4),
									  immediate(2), internet(6), network(7),
									  priority(1), routine(0), undefined(8) }
									
	-- Tos Value
		TosValue ::= INTEGER {
						normal(0),
						minMonetaryCost(1),
						maxReliability(2),
						tosValue3(3),
						maxThroughput(4),
						tosValue5(5),
						tosValue6(6),
						tosValue7(7),
						minDelay(8),
						tosValue9(9),
						tosValue10(10),
						tosValue11(11),
						tosValue12(12),
						tosValue13(13),
						tosValue14(14),
						tosValue15(15),
						undefined(16)
							}

	--  Direction 
		Direction ::= INTEGER { inbound(0), outbound(1) }
		
------Access Control List

snAgAcl		OBJECT IDENTIFIER ::= { snIp 15 }

snAgAclGlobal	OBJECT IDENTIFIER ::= { snAgAcl 1 }

snAgAclGblCurRowIndex OBJECT-TYPE
	SYNTAX	INTEGER 
	ACCESS	read-only
	STATUS	mandatory
	DESCRIPTION
		"The current row index of the ACL table entry."
	::= { snAgAclGlobal 1 }

--
-- ACL Table
--

snAgAclTable       OBJECT-TYPE
	SYNTAX  SEQUENCE OF SnAgAclEntry
	ACCESS  not-accessible
	STATUS  mandatory
	DESCRIPTION
		"Table of Access Control List"
	::= { snAgAcl 2 }

snAgAclEntry       OBJECT-TYPE
	SYNTAX  SnAgAclEntry
	ACCESS  not-accessible
	STATUS  mandatory
	DESCRIPTION
		"An entry in the IP access control list table."
	INDEX   { snAgAclIndex }
	::= { snAgAclTable 1 }

SnAgAclEntry ::= SEQUENCE {
	snAgAclIndex
		INTEGER,
	snAgAclNumber
		AclNumber,
	snAgAclName
		DisplayString,
	snAgAclAction              
		Action,
	snAgAclProtocol            
		IpProtocol,
	snAgAclSourceIp
		IpAddress,
	snAgAclSourceMask
		IpAddress,
	snAgAclSourceOperator
		Operator,
	snAgAclSourceOperand1
		INTEGER,
	snAgAclSourceOperand2
		INTEGER,
	snAgAclDestinationIp
		IpAddress,
	snAgAclDestinationMask
		IpAddress,
	snAgAclDestinationOperator
		Operator,
	snAgAclDestinationOperand1
		INTEGER,
	snAgAclDestinationOperand2
		INTEGER,
	snAgAclPrecedence
		PrecedenceValue,
	snAgAclTos
		TosValue,
	snAgAclEstablished
		RtrStatus,
	snAgAclLogOption
		TruthVal,
	snAgAclStandardFlag
		TruthVal,
	snAgAclRowStatus
		SnRowStatus,
	snAgAclFlowCounter
		Counter64,
	snAgAclPacketCounter
		Counter64,
	snAgAclComments
		DisplayString
	}

snAgAclIndex       OBJECT-TYPE
	SYNTAX  INTEGER
	ACCESS  read-only
	STATUS  mandatory
	DESCRIPTION
		"The access control list item number for an entry.
		This is a unique number that identifies different
		Access list entries combined with the access list
		name and access list number. This one has to be 
		unique even though the name and number are not unique
		for a give access list with same or different source
		address, subnet mask, destination address and destination
		mask, protocol type, action (permit/deny) type and the
		operator (neq, eq, gt and , lt) which makes the index a 
		unique tuple (name, number, itemnumber)."
	::= { snAgAclEntry 1 }

snAgAclNumber       OBJECT-TYPE
	SYNTAX  AclNumber
	ACCESS  read-write
	STATUS  mandatory
	DESCRIPTION
		"The access control list number for an entry.
		The standard access list is in the range <1..99>.
		The extended access list is in the range <100-199>."
	::= { snAgAclEntry 2 }

snAgAclName		OBJECT-TYPE
	SYNTAX  DisplayString
	ACCESS  read-write
	STATUS  mandatory
	DESCRIPTION
		"ACL name for an entry."
	::= { snAgAclEntry 3 }

snAgAclAction      OBJECT-TYPE
	SYNTAX  Action 
	ACCESS  read-write
	STATUS  mandatory
	DESCRIPTION
		"Action to take if the ip packet matches
		with this access control list."
	::= { snAgAclEntry 4 }

snAgAclProtocol    OBJECT-TYPE
	SYNTAX  IpProtocol
	ACCESS  read-write
	STATUS  mandatory
	DESCRIPTION
		"Transport protocol. 0 means any protocol."
	::= { snAgAclEntry 5 }

snAgAclSourceIp    OBJECT-TYPE
	SYNTAX  IpAddress
	ACCESS  read-write
	STATUS  mandatory
	DESCRIPTION
		"Source IP address."
	::= { snAgAclEntry 6 }

snAgAclSourceMask  OBJECT-TYPE
	SYNTAX  IpAddress
	ACCESS  read-write
	STATUS  mandatory
	DESCRIPTION
		"Source IP subnet mask."
	::= { snAgAclEntry 7 }

snAgAclSourceOperator    OBJECT-TYPE
	SYNTAX  Operator
	ACCESS  read-write
	STATUS  mandatory
	DESCRIPTION
		"Type of comparison to perform.
		for now, this only applys to tcp or udp
		to compare the port number"
	::= { snAgAclEntry 8 }

snAgAclSourceOperand1     OBJECT-TYPE
	SYNTAX  INTEGER(0..65535)
	ACCESS  read-write
	STATUS  mandatory
	DESCRIPTION
		"For now this only refers to transport 
		protocol port number. 0 means NA"
	::= { snAgAclEntry 9 }

snAgAclSourceOperand2     OBJECT-TYPE
	SYNTAX  INTEGER(0..65535)
	ACCESS  read-write
	STATUS  mandatory
	DESCRIPTION
		"For now this only refers to transport 
		protocol port number. 0 means NA"
	::= { snAgAclEntry 10 }

snAgAclDestinationIp      OBJECT-TYPE
	SYNTAX  IpAddress
	ACCESS  read-write
	STATUS  mandatory
	DESCRIPTION
		"Destination IP address."
	::= { snAgAclEntry 11 }

snAgAclDestinationMask    OBJECT-TYPE
	SYNTAX  IpAddress
	ACCESS  read-write
	STATUS  mandatory
	DESCRIPTION
		"Destination IP subnet mask."
	::= { snAgAclEntry 12 }

snAgAclDestinationOperator    OBJECT-TYPE
	SYNTAX  Operator
	ACCESS  read-write
	STATUS  mandatory
	DESCRIPTION
		"Type of comparison to perform.
		for now, this only applys to tcp or udp
		to compare the port number"
	::= { snAgAclEntry 13 }

snAgAclDestinationOperand1     OBJECT-TYPE
	SYNTAX  INTEGER(0..65535)
	ACCESS  read-write
	STATUS  mandatory
	DESCRIPTION
		"For now this only refers to transport 
		protocol port number. 0 means NA"
	::= { snAgAclEntry 14 }

snAgAclDestinationOperand2     OBJECT-TYPE
	SYNTAX  INTEGER(0..65535)
	ACCESS  read-write
	STATUS  mandatory
	DESCRIPTION
		"For now this only refers to transport 
		protocol port number. 0 means NA"
	::= { snAgAclEntry 15 }

snAgAclPrecedence OBJECT-TYPE
	SYNTAX  PrecedenceValue
	ACCESS  read-write
	STATUS  mandatory
	DESCRIPTION
		"This refers to IP precedence value in the range <0-7>
		critical(5), 
		flash(3), 
		flash-override(4), 
		immediate(2), 
		internet(6), 
		network(7), 
		priority(1), 
		routine(0)"
		::= { snAgAclEntry 16 }

snAgAclTos OBJECT-TYPE
	  SYNTAX  TosValue
	  ACCESS  read-write
	  STATUS  mandatory
	  DESCRIPTION
		"This refers to the IP type of service value in range
		<0-15> which is the sum of numeric vlaues of the 
		following options -
		match packets with maximum reliability TOS (2)
		match packets with maximum throughput TOS (4)
		match packets with minimum delay (8)
		match packets with minimum monetary cost TOS (1)
		match packets with normal TOS  (0)"
		::= { snAgAclEntry 17 }

snAgAclEstablished OBJECT-TYPE
	SYNTAX  RtrStatus
	ACCESS  read-write
	STATUS  mandatory
	DESCRIPTION
		"Enable/Disable the filtering of established TCP
		packets of which the ACK or RESET flag is on. This
		additional filter only applies to TCP transport
		protocol."
	::= { snAgAclEntry 18 }

snAgAclLogOption OBJECT-TYPE
	SYNTAX  TruthVal
	ACCESS  read-write
	STATUS  mandatory
	DESCRIPTION
		"Log flag"
	::= { snAgAclEntry 19 }

snAgAclStandardFlag OBJECT-TYPE
	SYNTAX  TruthVal
	ACCESS  read-write
	STATUS  mandatory
	DESCRIPTION
		"Return whether the ACL is standard or extended, 1 for standard ACL"
	::= { snAgAclEntry 20 }

snAgAclRowStatus   OBJECT-TYPE
	SYNTAX  SnRowStatus
	ACCESS  read-write
	STATUS  mandatory
	DESCRIPTION
		"To create or delete a access list
		entry."
	::= { snAgAclEntry 21 }

snAgAclFlowCounter   OBJECT-TYPE
	SYNTAX  Counter64
	ACCESS  read-only
	STATUS  mandatory
	DESCRIPTION
		"Approximate count of flows matching individual ACL entry."
	::= { snAgAclEntry 22 }

snAgAclPacketCounter   OBJECT-TYPE
	SYNTAX  Counter64
	ACCESS  read-only
	STATUS  mandatory
	DESCRIPTION
		"Accurate count of packets matching individual ACL entry."
	::= { snAgAclEntry 23 }

snAgAclComments   OBJECT-TYPE
	SYNTAX  DisplayString
	ACCESS  read-write
	STATUS  mandatory
	DESCRIPTION
		"Remark description of individual ACL entry."
	::= { snAgAclEntry 24 }

--
-- Acl Port Table

snAgAclBindToPortTable   OBJECT-TYPE
	SYNTAX  SEQUENCE OF SnAgAclBindToPortEntry
	ACCESS  not-accessible
	STATUS  mandatory
	DESCRIPTION
		"Table of ACL binding to port for router"
	::= { snAgAcl 3 }

snAgAclBindToPortEntry       OBJECT-TYPE
	SYNTAX  SnAgAclBindToPortEntry
	ACCESS  not-accessible
	STATUS  mandatory
	DESCRIPTION
		"An entry in the ACL-binding-to-port table."
	INDEX   { 
			   snAgAclPortNum, 
			   snAgAclPortBindDirection
			}
	::= { snAgAclBindToPortTable 1 }

SnAgAclBindToPortEntry ::= SEQUENCE {
	snAgAclPortNum
		INTEGER,
	snAgAclPortBindDirection
		Direction,
	snAgAclNum
		INTEGER,
	snAgAclNameString
		DisplayString,
	snAgBindPortListInVirtualInterface
		OCTET STRING,
	snAgAclPortRowStatus
		SnRowStatus
	}

snAgAclPortNum      OBJECT-TYPE
	SYNTAX  INTEGER
	ACCESS  read-only
	STATUS  mandatory
	DESCRIPTION
		"Binding-to port num, either physical port or virtual interface."
	::= { snAgAclBindToPortEntry 1 }

snAgAclPortBindDirection   OBJECT-TYPE
	SYNTAX  Direction
	ACCESS  read-only
	STATUS  mandatory
	DESCRIPTION
		"ACL port direction, inbound or outbound"
	::= { snAgAclBindToPortEntry 2 }

snAgAclNum      OBJECT-TYPE
	SYNTAX  INTEGER
	ACCESS  read-write
	STATUS  mandatory
	DESCRIPTION
		"Defined ACL number"
	::= { snAgAclBindToPortEntry 3 }

snAgAclNameString      OBJECT-TYPE
	SYNTAX  DisplayString
	ACCESS  read-write
	STATUS  mandatory
	DESCRIPTION
		"Defined ACL name"
	::= { snAgAclBindToPortEntry 4 }

snAgBindPortListInVirtualInterface   OBJECT-TYPE
	SYNTAX  OCTET STRING
	ACCESS  read-write
	STATUS  mandatory
	DESCRIPTION
		"Port list for binding virtual interface"
	::= { snAgAclBindToPortEntry 5 }

snAgAclPortRowStatus   OBJECT-TYPE
	SYNTAX  SnRowStatus
	ACCESS  read-write
	STATUS  mandatory
	DESCRIPTION
		"To create or delete a ACL port entry."
	::= { snAgAclBindToPortEntry 6 }

END
FOUNDRY-SN-WIRELESS-GROUP-MIB DEFINITIONS ::= BEGIN
-- Foundry SN WIRELESS GROUP MIB Release 1.0.0
-- Revision 0 04/15/04

-- Copyright 1996-2004 Foundry Networks, Inc.
-- All rights reserved.
-- This Foundry Networks SNMP Management Information Base Specification
-- (Specification) embodies Foundry Networks' confidential and
-- proprietary intellectual property. Foundry Networks retains all
-- title and ownership in the Specification, including any
-- revisions.

-- This Specification is supplied "AS IS," and Foundry Networks makes
-- no warranty, either express or implied, as to the use,
-- operation, condition, or performance of the Specification.

-- SECTION 1: Top Level Definitions

IMPORTS
	Counter, TimeTicks, IpAddress, Gauge, enterprises
		FROM RFC1155-SMI
	OBJECT-TYPE
		FROM RFC-1212
	snWireless
		FROM FOUNDRY-SN-SWITCH-GROUP-MIB;

-- textual conventions

    MacAddress
        ::= OCTET STRING (SIZE (6))
    DisplayString
        ::= OCTET STRING

    IfIndexList ::= TEXTUAL-CONVENTION
        STATUS      current
        DESCRIPTION
            "Each octet within this value specifies a set of eight
            interfaces by their ifIndex values, with the first octet
            specifying interfaces 1 through 8, the second octet
            specifying interfaces 9 through 16, etc.  Within each
            octet, the most significant bit represents the lowest
            numbered interface, and the least significant bit
            represents the highest numbered interface.  Thus, each
            interface of the device is represented by a single bit
            within the value of this object.  If that bit has a value
            of '1' then that interface is included in the set of
            interfaces; the interface is not included if its bit has a
            value of '0'."
        SYNTAX      OCTET STRING

-- iso(1).org(3).dod(6).internet(1).private(4).enterprises(1).foundry(1991)

wgGroup     OBJECT IDENTIFIER ::= { snWireless 1 }

wgMobilityId OBJECT-TYPE
	SYNTAX  INTEGER
	ACCESS  read-write
	STATUS  mandatory
	DESCRIPTION
        "Unique Identifier used to specify the mobility doamin.
         Valid range is <1 - 65535>. Use <0> to remove the domain."
	::= { wgGroup 1 }

wgVpnPTDeletePolicy OBJECT-TYPE
	SYNTAX  INTEGER
	ACCESS  read-write
	STATUS  mandatory
	DESCRIPTION
        "Write a valid VPN pass through policy ID to remove the policy.
		Return zero when reading this object."
	::= { wgGroup 2 }


--
-- WiFi Interface Table
--

wgIfTable OBJECT-TYPE
    SYNTAX SEQUENCE OF WgIfEntry
    ACCESS not-accessible
    STATUS mandatory
    DESCRIPTION
		"WiFi Interface Table."
    ::= { snWireless 2 }
    
wgIfEntry OBJECT-TYPE
    SYNTAX WgIfEntry
    ACCESS not-accessible
    STATUS mandatory
    DESCRIPTION
		"An entry of the WiFi Interface Table."
    INDEX { wgIfIndex }
    ::= { wgIfTable 1 }

WgIfEntry ::= SEQUENCE {
    wgIfIndex               INTEGER,
    wgIfWirelessEnable      INTEGER,
    wgIfPnPLearnNewAP       INTEGER,
    wgIfAutoPortDisable     INTEGER,
    wgIfVpnPTPolicyId       INTEGER
}

wgIfIndex OBJECT-TYPE
	SYNTAX  INTEGER
	ACCESS  read-only
	STATUS  mandatory
    DESCRIPTION
		"ifIndex value of the switch interface."
    ::= { wgIfEntry 1 }

wgIfWirelessEnable OBJECT-TYPE
	SYNTAX  INTEGER {
		other(1),
		enable(2),
		disable(3)
		}
	ACCESS  read-write
	STATUS  mandatory
    DESCRIPTION
		"Control wireless function of the switch interface."
	DEFVAL { disable }
    ::= { wgIfEntry 2 }

wgIfPnPLearnNewAP OBJECT-TYPE
	SYNTAX  INTEGER {
		other(1),
		enable(2),
		disable(3)
		}
	ACCESS  read-write
	STATUS  mandatory
	DESCRIPTION
		"Control the interface to learn new AP."
	::= { wgIfEntry 3 }

wgIfAutoPortDisable  OBJECT-TYPE
	SYNTAX  INTEGER {
		other(1),
		enable(2),
		disable(3)
		}
	ACCESS  read-write
	STATUS  mandatory
	DESCRIPTION
		"Disable the interface if the interface link status change."
	::= { wgIfEntry 4 }

wgIfVpnPTPolicyId OBJECT-TYPE
	SYNTAX  INTEGER
	ACCESS  read-write
	STATUS  mandatory
    DESCRIPTION
        "To bind an interface to a VPN pass through policy, write
        a valid policy number which is larger than zero. To unbind
        an interface to a VPN pass through policy, write a zero."
    ::= { wgIfEntry 5 }


--
-- Roaming Peer table
--

wgRoamingPeerTable OBJECT-TYPE
	SYNTAX  SEQUENCE OF WgRoamingPeerEntry
	ACCESS  not-accessible
	STATUS  mandatory
	DESCRIPTION
		"Roaming Peer table contains information of peers."
	::= { snWireless 3 }

wgRoamingPeerEntry OBJECT-TYPE
	SYNTAX  WgRoamingPeerEntry
	ACCESS  not-accessible
	STATUS  mandatory
	DESCRIPTION
		"An entry of the roaming peer table."
	INDEX   { wgRoamingPeerIpAddress }
	::= { wgRoamingPeerTable 1 }

WgRoamingPeerEntry ::= SEQUENCE {
	wgRoamingPeerIpAddress
		IpAddress,
	wgRoamingPeerConnectionStatus
		INTEGER,
	wgRoamingPeerRowStatus
		INTEGER
	}

wgRoamingPeerIpAddress OBJECT-TYPE
	SYNTAX  IpAddress
	ACCESS  read-only
	STATUS  mandatory
	DESCRIPTION
		"IP Address of the ISRP peer."
	::= { wgRoamingPeerEntry 1 }

wgRoamingPeerConnectionStatus OBJECT-TYPE
	SYNTAX  INTEGER {
		other(1),
		configured(2),
		established(3)
		}
	ACCESS  read-only
	STATUS  mandatory
	DESCRIPTION
		"Shows the state of the ISRP Connection."
	::= { wgRoamingPeerEntry 2 }

wgRoamingPeerRowStatus OBJECT-TYPE
	SYNTAX  INTEGER {
		other(1),
		valid(2),
		delete(3),
		create(4)
		}
	ACCESS  read-write
	STATUS  mandatory
	DESCRIPTION
		"Shows the state of the row in the PeerRow Table."
	::= { wgRoamingPeerEntry 3 }


--
-- AP Plug and Play Table
--

wgPnPTable OBJECT-TYPE
    SYNTAX SEQUENCE OF WgPnPEntry
    ACCESS not-accessible
    STATUS mandatory
    DESCRIPTION
		"AP Plug and Play Table."
    ::= { snWireless 4 }

wgPnPEntry OBJECT-TYPE
    SYNTAX WgPnPEntry
    ACCESS not-accessible
    STATUS mandatory
    DESCRIPTION
		"An entry of the AP Plug and Play Table."
    INDEX { wgPnPIfIndex, wgPnPMacAddress }
    ::= { wgPnPTable 1 }

WgPnPEntry ::= SEQUENCE {
    wgPnPIfIndex             INTEGER,
    wgPnPMacAddress          MacAddress,
    wgPnPIpAddress           IpAddress,
    wgPnPIpMask              IpAddress,
    wgPnPIpDefaultGw         IpAddress,
    wgPnPStatus              INTEGER,
    wgPnPRowStatus           INTEGER
}

wgPnPIfIndex OBJECT-TYPE
	SYNTAX  INTEGER
    ACCESS  read-only
    STATUS  mandatory
    DESCRIPTION
		"ifIndex value of the switch interface."
    ::= { wgPnPEntry 1 }

wgPnPMacAddress OBJECT-TYPE
    SYNTAX  MacAddress
    ACCESS  read-only
    STATUS  mandatory
    DESCRIPTION
		"MAC address of the attached AP."
    ::= { wgPnPEntry 2 }

wgPnPIpAddress OBJECT-TYPE
	SYNTAX  IpAddress
	ACCESS  read-write
	STATUS  mandatory
	DESCRIPTION
		"IP address of the attached AP."
    ::= { wgPnPEntry 3 }

wgPnPIpMask OBJECT-TYPE
	SYNTAX  IpAddress
	ACCESS  read-write
	STATUS  mandatory
	DESCRIPTION
		"Subnet mask of the attached AP."
    ::= { wgPnPEntry 4 }

wgPnPIpDefaultGw OBJECT-TYPE
	SYNTAX  IpAddress
	ACCESS  read-write
	STATUS  mandatory
	DESCRIPTION
		"Default gateway of the attached AP."
    ::= { wgPnPEntry 5 }

wgPnPStatus OBJECT-TYPE
	SYNTAX  INTEGER {
		other(1),
		discovered(2),
		configured(3),
		operational(4)
		}
	ACCESS  read-only
	STATUS  mandatory
	DESCRIPTION
		"AP device status. If the switch diecovered a new AP which
		had not been configured, the 'discovered' state will return.
		If the AP's IP address, subnet mask and default gateway were
		configured to the switch port but the AP with the matching
		MAC address had not attached to the switch port, 'configured'
		state will return. If the AP's IP address, subnet mask and
		default gateway were configured to the switch port and the
		AP with the matching MAC address had attached to the switch
		port and was operating, 'operational' state will return."
	::= { wgPnPEntry 6 }

wgPnPRowStatus OBJECT-TYPE
	SYNTAX  INTEGER {
		other(1),
		valid(2),
		delete(3),
		create(4),
		modify(5)
		}
	ACCESS  read-write
	STATUS  mandatory
	DESCRIPTION
		"Create, delete or modify a row of AP Plug and Play Table."
	::= { wgPnPEntry 7 }

--
-- VPN Pass Through Server Table
--

wgVpnPTServerTable OBJECT-TYPE
    SYNTAX SEQUENCE OF WgVpnPTServerEntry
    ACCESS not-accessible
    STATUS mandatory
    DESCRIPTION
		"VPN pass through server table"
    ::= { snWireless 5 }

wgVpnPTServerEntry OBJECT-TYPE
    SYNTAX WgVpnPTServerEntry
    ACCESS not-accessible
    STATUS mandatory
    DESCRIPTION
		"An entry of the VPN pass through server table."
    INDEX { wgVpnPTServerPolicyId, wgVpnPTServerIpAddress }
    ::= { wgVpnPTServerTable 1 }

WgVpnPTServerEntry ::= SEQUENCE {
    wgVpnPTServerPolicyId       INTEGER,
    wgVpnPTServerIpAddress      IpAddress,
    wgVpnPTServerRowStatus      INTEGER
}

wgVpnPTServerPolicyId OBJECT-TYPE
	SYNTAX  INTEGER
    ACCESS  read-only
	STATUS  mandatory
	DESCRIPTION
		"VPN pass through policy identifier. It must be greater than zero."
	::= { wgVpnPTServerEntry 1 }

wgVpnPTServerIpAddress OBJECT-TYPE
	SYNTAX  IpAddress
    ACCESS  read-only
	STATUS  mandatory
	DESCRIPTION
		"VPN server IP address."
	::= { wgVpnPTServerEntry 2 }

wgVpnPTServerRowStatus OBJECT-TYPE
	SYNTAX  INTEGER {
		other(1),
		valid(2),
		delete(3),
		create(4)
		}
	ACCESS  read-write
	STATUS  mandatory
	DESCRIPTION
		"Create or delete a row of VPN pass through server table."
	::= { wgVpnPTServerEntry 3 }


--
-- VPN Pass Through Filter Table
--

wgVpnPTFilterTable OBJECT-TYPE
    SYNTAX SEQUENCE OF WgVpnPTFilterEntry
    ACCESS not-accessible
    STATUS mandatory
    DESCRIPTION
		"VPN pass through filter table"
    ::= { snWireless 6 }

wgVpnPTFilterEntry OBJECT-TYPE
    SYNTAX WgVpnPTFilterEntry
    ACCESS not-accessible
    STATUS mandatory
    DESCRIPTION
		"An entry of the VPN pass through filter table."
    INDEX { wgVpnPTFilterPolicyId, wgVpnPTFilterProtocol, wgVpnPTFilterPort }
    ::= { wgVpnPTFilterTable 1 }

WgVpnPTFilterEntry ::= SEQUENCE {
    wgVpnPTFilterPolicyId       INTEGER,
    wgVpnPTFilterProtocol       INTEGER,
    wgVpnPTFilterPort           INTEGER,
    wgVpnPTFilterRowStatus      INTEGER
}

wgVpnPTFilterPolicyId OBJECT-TYPE
	SYNTAX  INTEGER
    ACCESS  read-only
	STATUS  mandatory
	DESCRIPTION
		"VPN pass through policy identifier. It must be greater than zero."
	::= { wgVpnPTFilterEntry 1 }

wgVpnPTFilterProtocol OBJECT-TYPE
	SYNTAX  INTEGER {
		other(1),
		udp(2),
		tcp(3)
		}
    ACCESS  read-only
	STATUS  mandatory
	DESCRIPTION
		"Allow this type of protocol to pass through."
	::= { wgVpnPTFilterEntry 2 }

wgVpnPTFilterPort OBJECT-TYPE
	SYNTAX  INTEGER
    ACCESS  read-only
	STATUS  mandatory
	DESCRIPTION
		"Allow this protocol port to pass through."
	::= { wgVpnPTFilterEntry 3 }

wgVpnPTFilterRowStatus OBJECT-TYPE
	SYNTAX  INTEGER {
		other(1),
		valid(2),
		delete(3),
		create(4)
		}
	ACCESS  read-write
	STATUS  mandatory
	DESCRIPTION
		"Create or delete a row of VPN pass through filter table."
	::= { wgVpnPTFilterEntry 4 }

--
-- VPN Pass Through Policy Table
--

wgVpnPTPolicyTable OBJECT-TYPE
    SYNTAX SEQUENCE OF WgVpnPTPolicyEntry
    ACCESS not-accessible
    STATUS mandatory
    DESCRIPTION
		"VPN pass through policy table"
    ::= { snWireless 7 }

wgVpnPTPolicyEntry OBJECT-TYPE
    SYNTAX WgVpnPTPolicyEntry
    ACCESS not-accessible
    STATUS mandatory
    DESCRIPTION
		"An entry of the VPN pass through policy table."
    INDEX { wgVpnPTPolicyId }
    ::= { wgVpnPTPolicyTable 1 }

WgVpnPTPolicyEntry ::= SEQUENCE {
    wgVpnPTPolicyId        INTEGER,
    wgVpnPTPolicyPortList  IfIndexList
}

wgVpnPTPolicyId OBJECT-TYPE
	SYNTAX  INTEGER
    ACCESS  read-only
	STATUS  mandatory
	DESCRIPTION
		"VPN pass through policy identifier. It must be greater than zero."
	::= { wgVpnPTPolicyEntry 1 }

wgVpnPTPolicyPortList OBJECT-TYPE
	SYNTAX  IfIndexList
	ACCESS  read-only
	STATUS  mandatory
	DESCRIPTION
		"A list of ports bound to this VPN pass through policy."
	::= { wgVpnPTPolicyEntry 2 }

END
FOUNDRY-SN-TRAP-MIB DEFINITIONS ::= BEGIN

-- Router Switch Trap MIB Release 1.0.0
-- Revision 06/02/97

-- Copyright 1996-1997 Foundry Networks, Inc.
-- All rights reserved.
-- This Foundry SNMP Management Information Base Specification
-- (Specification) embodies Foundry's confidential and
-- proprietary intellectual property. Foundry retains all
-- title and ownership in the Specification, including any
-- revisions.

-- This Specification is supplied "AS IS," and Foundry makes
-- no warranty, either express or implied, as to the use,
-- operation, condition, or performance of the Specification.

-- SECTION 1: Top Level Definitions


-- Imports


IMPORTS
   TRAP-TYPE              FROM RFC-1215
   ifIndex                FROM IF-MIB
   foundry                FROM FOUNDRY-SN-ROOT-MIB
   snVLanByPortCfgVLanId  FROM FOUNDRY-SN-SWITCH-GROUP-MIB
   snAgGblTrapMessage,
   snAgentBrdIndex,
   snChasPwrSupplyIndex,
   snChasPwrSupplyDescription,
   snChasFanIndex,
   snChasFanDescription   FROM FOUNDRY-SN-AGENT-MIB
   snL4TrapLinkName,
   snL4LinkVirtualInterface,
   snL4MaxSessionLimit,
   snL4TcpSynLimit,
   snL4TrapRealServerIP, 
   snL4TrapRealServerName,
   snL4TrapRealServerPort,
   snL4TrapRealServerCurConnections FROM FOUNDRY-SN-SW-L4-SWITCH-GROUP-MIB
   wgPnPIfIndex,
   wgPnPMacAddress,
   wgPnPStatus FROM FOUNDRY-SN-WIRELESS-GROUP-MIB;


-- Textual Conventions

-- Groups

-- SECTION 2: MIB Objects


-- Trap Information

-- These definitions use the TRAP-TYPE macro as defined in RFC 1215.

-- Foundry Networks, Inc. Specific Traps

-- Trap IDs 1 and 2 are not used now as they are obseleted.

-- Trap IDs from 3 through 18 are used by OSPF. See Router Trap mib for definitions.

snTrapL4MaxSessionLimitReached TRAP-TYPE
   ENTERPRISE foundry
   VARIABLES { snL4MaxSessionLimit }
   DESCRIPTION
       "The SNMP trap that is generated when the maximum number
       of connections reached."
	--#TYPE "Foundry Trap: L4 Session Limit"
	--#SUMMARY "SLB maximum number of connections  %d has been reached."
	--#ARGUMENTS { 0 }
	--#SEVERITY WARNING
	--#STATE OPERATIONAL
   ::= 19


snTrapL4TcpSynLimitReached TRAP-TYPE
   ENTERPRISE foundry
   VARIABLES { snL4TcpSynLimit }
   DESCRIPTION
       "The SNMP trap that is generated when the number of TCP
       SYN limits reached."
	--#TYPE "Foundry Trap: L4 TCP Syn Limit"
	--#SUMMARY "SLB TCP Syn limits %d has been reached."
	--#ARGUMENTS { 0 }
	--#SEVERITY WARNING
	--#STATE OPERATIONAL
   ::= 20


snTrapL4RealServerUp TRAP-TYPE
   ENTERPRISE foundry
   VARIABLES { snL4TrapRealServerIP, snL4TrapRealServerName }
   DESCRIPTION
       "The SNMP trap that is generated when the load balancing
       real server is up."
	--#TYPE "Foundry Trap: L4 Real Server Up"
	--#SUMMARY "SLB real server %s %s is up."
	--#ARGUMENTS { 0, 1 }
	--#SEVERITY INFORMATIONAL
	--#STATE OPERATIONAL
   ::= 21


snTrapL4RealServerDown TRAP-TYPE
   ENTERPRISE foundry
   VARIABLES { snL4TrapRealServerIP, snL4TrapRealServerName }
   DESCRIPTION
       "The SNMP trap that is generated when the load balancing
       real server is down."
	--#TYPE "Foundry Trap: L4 Real Server Down"
	--#SUMMARY "SLB real server %s %s is down."
	--#ARGUMENTS { 0, 1 }
	--#SEVERITY INFORMATIONAL
	--#STATE OPERATIONAL
   ::= 22


snTrapL4RealServerPortUp TRAP-TYPE
   ENTERPRISE foundry
   VARIABLES { snL4TrapRealServerIP, snL4TrapRealServerName, snL4TrapRealServerPort }
   DESCRIPTION
       "The SNMP trap that is generated when the load balancing
       real server TCP port is up."
	--#TYPE "Foundry Trap: L4 Real Server Port Up"
	--#SUMMARY "SLB real server port %s %s %d is up."
	--#ARGUMENTS { 0, 1, 2 }
	--#SEVERITY INFORMATIONAL
	--#STATE OPERATIONAL
   ::= 23


snTrapL4RealServerPortDown TRAP-TYPE
   ENTERPRISE foundry
   VARIABLES { snL4TrapRealServerIP, snL4TrapRealServerName, snL4TrapRealServerPort }
   DESCRIPTION
       "The SNMP trap that is generated when the load balancing
       real server TCP port is down."
	--#TYPE "Foundry Trap: L4 Real Server Port Down"
	--#SUMMARY "SLB real server port %s %s %d is down."
	--#ARGUMENTS { 0, 1, 2 }
	--#SEVERITY INFORMATIONAL
	--#STATE OPERATIONAL
   ::= 24


snTrapL4RealServerMaxConnectionLimitReached TRAP-TYPE
   ENTERPRISE foundry
   VARIABLES { snL4TrapRealServerIP, snL4TrapRealServerName, snL4TrapRealServerCurConnections }
   DESCRIPTION
       "The SNMP trap that is generated when the real server reaches
       maximum number of connections."
	--#TYPE "Foundry Trap: L4 Real Server Max Connection Limit"
	--#SUMMARY "SLB real server %s %s maximum connection %d has been reached."
	--#ARGUMENTS { 0, 1, 2 }
	--#SEVERITY WARNING
	--#STATE OPERATIONAL
   ::= 25


snTrapL4BecomeStandby TRAP-TYPE
   ENTERPRISE foundry
   DESCRIPTION
       "The SNMP trap that is generated when the server load
       balancing switch changes state from active to standby."
	--#TYPE "Foundry Trap: L4 Server On Standby"
	--#SUMMARY "SLB changes state from active to standby."
	--#ARGUMENTS { }
	--#SEVERITY WARNING
	--#STATE OPERATIONAL
   ::= 26


snTrapL4BecomeActive TRAP-TYPE
   ENTERPRISE foundry
   DESCRIPTION
       "The SNMP trap that is generated when the server load
       balancing switch changes state from standby to active."
	--#TYPE "Foundry Trap: L4 Server Active"
	--#SUMMARY "SLB changes state from standby to active."
	--#ARGUMENTS { }
	--#SEVERITY WARNING
	--#STATE OPERATIONAL
   ::= 27


snTrapModuleInserted TRAP-TYPE
   ENTERPRISE foundry
   VARIABLES { snAgentBrdIndex }
   DESCRIPTION
       "The SNMP trap that is generated when a module was inserted
       to the chassis during system running."
	--#TYPE "Foundry Trap: Module Inserted"
	--#SUMMARY "Module %d was inserted to the chassis during system running."
	--#ARGUMENTS { 0 }
	--#SEVERITY INFORMATIONAL
	--#STATE OPERATIONAL
   ::= 28


snTrapModuleRemoved TRAP-TYPE
   ENTERPRISE foundry
   VARIABLES { snAgentBrdIndex }
   DESCRIPTION
       "The SNMP trap that is generated when a module was removed
       from the chassis during system running."
	--#TYPE "Foundry Trap: Module Removed"
	--#SUMMARY "Module %d was removed from the chassis during system running."
	--#ARGUMENTS { 0 }
	--#SEVERITY INFORMATIONAL
	--#STATE OPERATIONAL
   ::= 29


snTrapChasPwrSupplyFailed TRAP-TYPE
   ENTERPRISE foundry
   VARIABLES { snChasPwrSupplyIndex, snChasPwrSupplyDescription }
   DESCRIPTION
       "The SNMP trap that is generated when a power supply fails
        to operate normally."
	--#TYPE "Foundry Trap: Power Supply Failure"
	--#SUMMARY "Power supply %d (%s)  failed."
	--#ARGUMENTS { 0, 1 }
	--#SEVERITY MINOR
	--#STATE OPERATIONAL
   ::= 30


snTrapChasFanFailed TRAP-TYPE
   ENTERPRISE foundry
   VARIABLES { snChasFanIndex, snChasFanDescription }
   DESCRIPTION
       "The SNMP trap that is generated when a fan fails
        to operate normally."
	--#TYPE "Foundry Trap: Fan Failure"
	--#SUMMARY "Fan  %d (%s)  failed."
	--#ARGUMENTS { 0, 1 }
	--#SEVERITY MINOR
	--#STATE OPERATIONAL
   ::= 31


snTrapLockedAddressViolation2 TRAP-TYPE
   ENTERPRISE foundry
   VARIABLES { snAgGblTrapMessage }
   DESCRIPTION
       "The SNMP trap that is generated when more source MAC addresses
        are received from a port than the maximum number of addresses
        configured to that port."
	--#TYPE "Foundry Trap: Lock Address Violation"
	--#SUMMARY "%s."
	--#ARGUMENTS { 0 }
	--#SEVERITY MINOR
	--#STATE OPERATIONAL
   ::= 32


snTrapFsrpIfStateChange TRAP-TYPE
   ENTERPRISE foundry
   VARIABLES { snAgGblTrapMessage }
   DESCRIPTION
       "The SNMP trap that is generated when a FSRP routing device
       changed state from active to standby or vice-versa."
	--#TYPE "Foundry Trap: FSRP Interface Change"
	--#SUMMARY "%s."
	--#ARGUMENTS { 0 }
	--#SEVERITY INFORMATIONAL
	--#STATE OPERATIONAL
   ::= 33

snTrapVrrpIfStateChange TRAP-TYPE
   ENTERPRISE foundry
   VARIABLES { snAgGblTrapMessage }
   DESCRIPTION
       "The SNMP trap that is generated when a VRRP routing device
       changed state from master to backup or vice-versa."
	--#TYPE "Foundry Trap: VRRP Interface Change"
	--#SUMMARY "%s."
	--#ARGUMENTS { 0 }
	--#SEVERITY WARNING
	--#STATE OPERATIONAL
   ::= 34


snTrapMgmtModuleRedunStateChange TRAP-TYPE
   ENTERPRISE foundry
   VARIABLES { snAgGblTrapMessage }
   DESCRIPTION
       "The SNMP trap that is generated when the management module
       changes redundancy state."
	--#TYPE "Foundry Trap: Management Module Change State"
	--#SUMMARY "%s."
	--#ARGUMENTS { 0 }
	--#SEVERITY WARNING
	--#STATE OPERATIONAL
   ::= 35


snTrapTemperatureWarning TRAP-TYPE
   ENTERPRISE foundry
   VARIABLES { snAgGblTrapMessage }
   DESCRIPTION
       "The SNMP trap that is generated when the actual temperature
       reading is above the warning temperature threshold."
	--#TYPE "Foundry Trap: Temperature Warning"
	--#SUMMARY "%s."
	--#ARGUMENTS { 0 }
	--#SEVERITY CRITICAL
	--#STATE OPERATIONAL
   ::= 36

snTrapAccessListDeny TRAP-TYPE
   ENTERPRISE foundry
   VARIABLES { snAgGblTrapMessage }
   DESCRIPTION
       "The SNMP trap that is generated when a packet was denied
       by an access list."
	--#TYPE "Foundry Trap: Deny from ACL"
	--#SUMMARY "%s."
	--#ARGUMENTS { 0 }
	--#SEVERITY WARNING
	--#STATE OPERATIONAL
   ::= 37

snTrapMacFilterDeny TRAP-TYPE
   ENTERPRISE foundry
   VARIABLES { snAgGblTrapMessage }
   DESCRIPTION
       "The SNMP trap that is generated when a packet was denied
       by a MAC address filter."
	--#TYPE "Foundry Trap: Deny from MAC Filter"
	--#SUMMARY "%s."
	--#ARGUMENTS { 0 }
	--#SEVERITY WARNING
	--#STATE OPERATIONAL
   ::= 38

snTrapL4GslbRemoteUp TRAP-TYPE
   ENTERPRISE foundry
   VARIABLES { snAgGblTrapMessage }
   DESCRIPTION
       "The SNMP trap that is generated when the connection to the remote SI is established."
	--#TYPE "Foundry Trap: Remote SI Up"
	--#SUMMARY "%s."
	--#ARGUMENTS { 0 }
	--#SEVERITY WARNING
	--#STATE OPERATIONAL
   ::= 39

snTrapL4GslbRemoteDown TRAP-TYPE
   ENTERPRISE foundry
   VARIABLES { snAgGblTrapMessage }
   DESCRIPTION
       "The SNMP trap that is generated when the connection to the remote SI is down."
	--#TYPE "Foundry Trap: Remote SI Down"
	--#SUMMARY "%s."
	--#ARGUMENTS { 0 }
	--#SEVERITY WARNING
	--#STATE OPERATIONAL
   ::= 40

snTrapL4GslbRemoteControllerUp TRAP-TYPE
   ENTERPRISE foundry
   VARIABLES { snAgGblTrapMessage }
   DESCRIPTION
       "The SNMP trap that is generated when the connection to the GSLB SI is established."
	--#TYPE "Foundry Trap: Remote GSLB SI Up"
	--#SUMMARY "%s."
	--#ARGUMENTS { 0 }
	--#SEVERITY WARNING
	--#STATE OPERATIONAL
   ::= 41

snTrapL4GslbRemoteControllerDown TRAP-TYPE
   ENTERPRISE foundry
   VARIABLES { snAgGblTrapMessage }
   DESCRIPTION
       "The SNMP trap that is generated when the connection to the GSLB SI is down."
	--#TYPE "Foundry Trap: Remote GSLB SI Down"
	--#SUMMARY "%s."
	--#ARGUMENTS { 0 }
	--#SEVERITY WARNING
	--#STATE OPERATIONAL
   ::= 42

snTrapL4GslbHealthCheckIpUp TRAP-TYPE
   ENTERPRISE foundry
   VARIABLES { snAgGblTrapMessage }
   DESCRIPTION
       "The SNMP trap that is generated when GSLB health check for an address transitions
	   from down to active state."
	--#TYPE "Foundry Trap: GSLB HealtCheck Up"
	--#SUMMARY "%s."
	--#ARGUMENTS { 0 }
	--#SEVERITY WARNING
	--#STATE OPERATIONAL
   ::= 43

snTrapL4GslbHealthCheckIpDown TRAP-TYPE
   ENTERPRISE foundry
   VARIABLES { snAgGblTrapMessage }
   DESCRIPTION
       "The SNMP trap that is generated when GSLB health check for an address transitions
	   from active to down state."
	--#TYPE "Foundry Trap: GSLB HealthCheck Down"
	--#SUMMARY "%s."
	--#ARGUMENTS { 0 }
	--#SEVERITY WARNING
	--#STATE OPERATIONAL
   ::= 44

snTrapL4GslbHealthCheckIpPortUp TRAP-TYPE
   ENTERPRISE foundry
   VARIABLES { snAgGblTrapMessage }
   DESCRIPTION
       "The SNMP trap that is generated when a given port for a health check address is up."
	--#TYPE "Foundry Trap: GSLB HealthCheck Port Up"
	--#SUMMARY "%s."
	--#ARGUMENTS { 0 }
	--#SEVERITY WARNING
	--#STATE OPERATIONAL
   ::= 45

snTrapL4GslbHealthCheckIpPortDown TRAP-TYPE
   ENTERPRISE foundry
   VARIABLES { snAgGblTrapMessage }
   DESCRIPTION
       "The SNMP trap that is generated when a given port for a health check address is down."
	--#TYPE "Foundry Trap: GSLB HealthCheck Port Down"
	--#SUMMARY "%s."
	--#ARGUMENTS { 0 }
	--#SEVERITY WARNING
	--#STATE OPERATIONAL
   ::= 46

snTrapL4FirewallBecomeStandby TRAP-TYPE
   ENTERPRISE foundry
   DESCRIPTION
       "The SNMP trap that is generated when the server load
       balancing switch Firewall changes state from active to standby."
	--#TYPE "Foundry Trap: Firewall Standby"
	--#SUMMARY "Firewall changes state from active to standby."
	--#ARGUMENTS { }
	--#SEVERITY MAJOR
	--#STATE OPERATIONAL
   ::= 47


snTrapL4FirewallBecomeActive TRAP-TYPE
   ENTERPRISE foundry
   DESCRIPTION
       "The SNMP trap that is generated when the server load
       balancing switch Firewall changes state from standby to active."
	--#TYPE "Foundry Trap: Firewall Active"
	--#SUMMARY "Firewall changes state from standby to active."
	--#ARGUMENTS { }
	--#SEVERITY MAJOR
	--#STATE OPERATIONAL
   ::= 48

snTrapL4FirewallPathUp TRAP-TYPE
   ENTERPRISE foundry
   DESCRIPTION
       "The SNMP trap that is generated when the server load
       balancing switch Firewall path is up."
	--#TYPE "Foundry Trap: Firewall Path Up"
	--#SUMMARY "Firewall path is up."
	--#ARGUMENTS { }
	--#SEVERITY MINOR
	--#STATE OPERATIONAL
   ::= 49


snTrapL4FirewallPathDown TRAP-TYPE
   ENTERPRISE foundry
   DESCRIPTION
       "The SNMP trap that is generated when the server load
       balancing switch Firewall path is down."
	--#TYPE "Foundry Trap: Firewall Path Down"
	--#SUMMARY "Firewall path is down."
	--#ARGUMENTS { }
	--#SEVERITY MINOR
	--#STATE OPERATIONAL
   ::= 50

snTrapIcmpLocalExceedBurst TRAP-TYPE
   ENTERPRISE foundry
   VARIABLES { snAgGblTrapMessage }
   DESCRIPTION
       "The SNMP trap that is generated when incoming ICMP exceeds burst-MAX."
	--#TYPE "Foundry Trap: ICMP Burst Exceeded"
	--#SUMMARY "%s."
	--#ARGUMENTS { 0 }
	--#SEVERITY WARNING
	--#STATE OPERATIONAL
   ::= 51

snTrapIcmpTransitExceedBurst TRAP-TYPE
   ENTERPRISE foundry
   VARIABLES { snAgGblTrapMessage }
   DESCRIPTION
       "The SNMP trap that is generated when transit ICMP exceeds burst-MAX."
	--#TYPE "Foundry Trap: Transit ICMP Burst Exceeded"
	--#SUMMARY "%s."
	--#ARGUMENTS { 0 }
	--#SEVERITY WARNING
	--#STATE OPERATIONAL
   ::= 52

snTrapTcpLocalExceedBurst TRAP-TYPE
   ENTERPRISE foundry
   VARIABLES { snAgGblTrapMessage }
   DESCRIPTION
       "The SNMP trap that is generated when incoming TCP SYN exceeds burst-MAX."
	--#TYPE "Foundry Trap: TCP SYN Burst Exceeded"
	--#SUMMARY "%s."
	--#ARGUMENTS { 0 }
	--#SEVERITY WARNING
	--#STATE OPERATIONAL
   ::= 53

snTrapTcpTransitExceedBurst TRAP-TYPE
   ENTERPRISE foundry
   VARIABLES { snAgGblTrapMessage }
   DESCRIPTION
       "The SNMP trap that is generated when transit TCP exceeds burst-MAX."
	--#TYPE "Foundry Trap: Transit TCP SYN Burst Exceeded"
	--#SUMMARY "%s."
	--#ARGUMENTS { 0 }
	--#SEVERITY WARNING
	--#STATE OPERATIONAL
   ::= 54

snTrapL4ContentVerification TRAP-TYPE
   ENTERPRISE foundry
   DESCRIPTION
       "The SNMP trap that is generated when the HTTP match-list pattern
       is found."
	--#TYPE "Foundry Trap: HTTP Match"
	--#SUMMARY "HTTP match-list pattern is found."
	--#ARGUMENTS { }
	--#SEVERITY INFORMATIONAL
	--#STATE OPERATIONAL
   ::= 55

snTrapDuplicateIp TRAP-TYPE
   ENTERPRISE foundry
   DESCRIPTION
       "Duplicate IP address detected."
	--#TYPE "Foundry Trap: Duplicate IP"
	--#SUMMARY "Duplicate IP address detect."
	--#ARGUMENTS { }
	--#SEVERITY MAJOR
	--#STATE OPERATIONAL
   ::= 56

snTrapMplsProblem TRAP-TYPE
   ENTERPRISE foundry
   DESCRIPTION
       "MPLS Problem Detected."
	--#TYPE "Foundry Trap: MPLS Problem"
	--#SUMMARY "MPLS Problem detect."
	--#ARGUMENTS { }
	--#SEVERITY MAJOR
	--#STATE OPERATIONAL
   ::= 57

snTrapMplsException TRAP-TYPE
   ENTERPRISE foundry
   DESCRIPTION
       "MPLS Exception Detected."
	--#TYPE "Foundry Trap: MPLS Exception"
	--#SUMMARY "MPLS Exception detect."
	--#ARGUMENTS { }
	--#SEVERITY MAJOR
	--#STATE OPERATIONAL
   ::= 58
   
snTrapMplsAudit TRAP-TYPE
   ENTERPRISE foundry
   DESCRIPTION
       "MPLS Audit Trap."
	--#TYPE "Foundry Trap: MPLS Audit"
	--#SUMMARY "MPLS Audit Trap."
	--#ARGUMENTS { }
	--#SEVERITY INFORMATIONAL
	--#STATE OPERATIONAL
   ::= 59
   
snTrapMplsDeveloper TRAP-TYPE
   ENTERPRISE foundry
   DESCRIPTION
       "MPLS Developer Trap."
	--#TYPE "Foundry Trap: MPLS Developer"
	--#SUMMARY "MPLS Developer Trap."
	--#ARGUMENTS { }
	--#SEVERITY INFORMATIONAL
	--#STATE OPERATIONAL
   ::= 60

snTrapNoBmFreeQueue TRAP-TYPE
   ENTERPRISE foundry
   VARIABLES { snAgGblTrapMessage }
   DESCRIPTION
       "The SNMP trap that is generated when no free queue is available in buffer manager."
	--#TYPE "Foundry Trap: No BM Free Queue"
	--#SUMMARY "%s."
	--#ARGUMENTS { 0 }
	--#SEVERITY WARNING
	--#STATE OPERATIONAL
   ::= 61

snTrapSmcDmaDrop TRAP-TYPE
   ENTERPRISE foundry
   VARIABLES { snAgGblTrapMessage }
   DESCRIPTION
       "The SNMP trap that is generated when SMC DMA packet is dropped."
	--#TYPE "Foundry Trap: SMC DMA Packet Dropped"
	--#SUMMARY "%s."
	--#ARGUMENTS { 0 }
	--#SEVERITY INFORMATIONAL
	--#STATE OPERATIONAL
   ::= 62

snTrapSmcBpDrop TRAP-TYPE
   ENTERPRISE foundry
   VARIABLES { snAgGblTrapMessage }
   DESCRIPTION
       "The SNMP trap that is generated when SMC BackPlane packet is dropped."
	--#TYPE "Foundry Trap: SMC BP Packet Dropped"
	--#SUMMARY "%s."
	--#ARGUMENTS { 0 }
	--#SEVERITY INFORMATIONAL
	--#STATE OPERATIONAL
   ::= 63

snTrapBmWriteSeqDrop TRAP-TYPE
   ENTERPRISE foundry
   VARIABLES { snAgGblTrapMessage }
   DESCRIPTION
       "The SNMP trap that is generated when BM write sequence packet is dropped."
	--#TYPE "Foundry Trap: BM Write Sequence Packet Dropped"
	--#SUMMARY "%s."
	--#ARGUMENTS { 0 }
	--#SEVERITY INFORMATIONAL
	--#STATE OPERATIONAL
   ::= 64

snTrapBgpPeerUp TRAP-TYPE
   ENTERPRISE foundry
   VARIABLES { snAgGblTrapMessage }
   DESCRIPTION
       "The SNMP trap that is generated when the bgp peer is up."
	--#TYPE "Foundry Trap: BGP Peer Up"
	--#SUMMARY "%s."
	--#ARGUMENTS { 0 }
	--#SEVERITY INFORMATIONAL
	--#STATE OPERATIONAL
   ::= 65

snTrapBgpPeerDown TRAP-TYPE
   ENTERPRISE foundry
   VARIABLES { snAgGblTrapMessage }
   DESCRIPTION
       "The SNMP trap that is generated when the bgp peer is down."
	--#TYPE "Foundry Trap: BGP Peer Down"
	--#SUMMARY "%s."
	--#ARGUMENTS { 0 }
	--#SEVERITY INFORMATIONAL
	--#STATE OPERATIONAL
   ::= 66

snTrapL4RealServerResponseTimeLowerLimit TRAP-TYPE
   ENTERPRISE foundry
   VARIABLES { snAgGblTrapMessage }
   DESCRIPTION
       "The SNMP trap that is generated when the real server average response time exceeds lower threshold."
	--#TYPE "Foundry Trap: L4 Real Server Response Exceeds Lower Threshold"
	--#SUMMARY "%s."
	--#ARGUMENTS { 0 }
	--#SEVERITY WARNING
	--#STATE OPERATIONAL
   ::= 67

snTrapL4RealServerResponseTimeUpperLimit TRAP-TYPE
   ENTERPRISE foundry
   VARIABLES { snAgGblTrapMessage }
   DESCRIPTION
       "The SNMP trap that is generated when the real server average response time exceeds upper threshold."
	--#TYPE "Foundry Trap: L4 Real Server Response Exceeds Upper Threshold"
	--#SUMMARY "%s."
	--#ARGUMENTS { 0 }
	--#SEVERITY WARNING
	--#STATE OPERATIONAL
   ::= 68

snTrapL4TcpAttackRateExceedMax TRAP-TYPE
   ENTERPRISE foundry
   VARIABLES { snAgGblTrapMessage }
   DESCRIPTION
       "The SNMP trap that is generated when the TCP attack rate exceeds configured maximum."
	--#TYPE "Foundry Trap: L4 TCP Attack Rate Exceed Max"
	--#SUMMARY "%s."
	--#ARGUMENTS { 0 }
	--#SEVERITY CRITICAL
	--#STATE OPERATIONAL
   ::= 69

snTrapL4TcpAttackRateExceedThreshold TRAP-TYPE
   ENTERPRISE foundry
   VARIABLES { snAgGblTrapMessage }
   DESCRIPTION
       "The SNMP trap that is generated when the TCP attack rate exceeds 80% of configured maximum."
	--#TYPE "Foundry Trap: L4 TCP Attack Rate Exceed Threshold"
	--#SUMMARY "%s."
	--#ARGUMENTS { 0 }
	--#SEVERITY WARNING
	--#STATE OPERATIONAL
   ::= 70

snTrapL4ConnectionRateExceedMax TRAP-TYPE
   ENTERPRISE foundry
   VARIABLES { snAgGblTrapMessage }
   DESCRIPTION
       "The SNMP trap that is generated when the L4 connection rate exceeds configured maximum."
	--#TYPE "Foundry Trap: L4 Connection Rate Exceed Max"
	--#SUMMARY "%s."
	--#ARGUMENTS { 0 }
	--#SEVERITY CRITICAL
	--#STATE OPERATIONAL
   ::= 71

snTrapL4ConnectionRateExceedThreshold TRAP-TYPE
   ENTERPRISE foundry
   VARIABLES { snAgGblTrapMessage }
   DESCRIPTION
       "The SNMP trap that is generated when the L4 connection rate exceeds 80% of configured maximum"
	--#TYPE "Foundry Trap: L4 Connection Rate Exceed Threshold"
	--#SUMMARY "%s."
	--#ARGUMENTS { 0 }
	--#SEVERITY WARNING
	--#STATE OPERATIONAL
   ::= 72

snTrapRunningConfigChanged TRAP-TYPE
   ENTERPRISE foundry
   VARIABLES { snAgGblTrapMessage }
   DESCRIPTION
       "The SNMP trap that is generated when the running configuration
        was changed."
	--#TYPE "Foundry Trap: Running Configuration Changed"
	--#SUMMARY "%s."
	--#ARGUMENTS { 0 }
	--#SEVERITY INFORMATIONAL
	--#STATE OPERATIONAL
   ::= 73

snTrapStartupConfigChanged TRAP-TYPE
   ENTERPRISE foundry
   VARIABLES { snAgGblTrapMessage }
   DESCRIPTION
       "The SNMP trap that is generated when the startup configuration
        was changed."
	--#TYPE "Foundry Trap: Startup Configuration Changed"
	--#SUMMARY "%s."
	--#ARGUMENTS { 0 }
	--#SEVERITY INFORMATIONAL
	--#STATE OPERATIONAL
   ::= 74

snTrapUserLogin TRAP-TYPE
   ENTERPRISE foundry
   VARIABLES { snAgGblTrapMessage }
   DESCRIPTION
       "The SNMP trap that is generated when user login."
	--#TYPE "Foundry Trap: User Login"
	--#SUMMARY "%s."
	--#ARGUMENTS { 0 }
	--#SEVERITY INFORMATIONAL
	--#STATE OPERATIONAL
   ::= 75

snTrapUserLogout TRAP-TYPE
   ENTERPRISE foundry
   VARIABLES { snAgGblTrapMessage }
   DESCRIPTION
       "The SNMP trap that is generated when user logout."
	--#TYPE "Foundry Trap: User Logout"
	--#SUMMARY "%s."
	--#ARGUMENTS { 0 }
	--#SEVERITY INFORMATIONAL
	--#STATE OPERATIONAL
   ::= 76

snTrapPortSecurityViolation TRAP-TYPE
   ENTERPRISE foundry
   VARIABLES { snAgGblTrapMessage }
   DESCRIPTION
       "The SNMP trap that is generated when insecure MAC addresses
        are received from a port with MAC security feature enabled."
	--#TYPE "Foundry Trap: Port Security Violation"
	--#SUMMARY "%s."
	--#ARGUMENTS { 0 }
	--#SEVERITY MINOR
	--#STATE OPERATIONAL
   ::= 77

snTrapPortSecurityShutdown TRAP-TYPE
   ENTERPRISE foundry
   VARIABLES { snAgGblTrapMessage }
   DESCRIPTION
       "The SNMP trap that is generated when insecure MAC addresses
        are received from a port caused the port to shutdown."
	--#TYPE "Foundry Trap: Port Security Violation Cause Shutdown"
	--#SUMMARY "%s."
	--#ARGUMENTS { 0 }
	--#SEVERITY MINOR
	--#STATE OPERATIONAL
   ::= 78

snTrapMrpStateChange TRAP-TYPE
   ENTERPRISE foundry
   VARIABLES { snAgGblTrapMessage }
   DESCRIPTION
       "The SNMP trap that is generated when a MRP switching and routing device
       changed state to  disabled, blocking, preforwarding, forwarding, uknown."
	--#TYPE "Foundry Trap: MRP Interface Change"
	--#SUMMARY "%s."
	--#ARGUMENTS { 0 }
	--#SEVERITY WARNING
	--#STATE OPERATIONAL
   ::= 79

snTrapMrpCamError TRAP-TYPE
   ENTERPRISE foundry
   VARIABLES { snAgGblTrapMessage }
   DESCRIPTION
       "The SNMP trap that is generated when a MRP Cam Error occurs."
	--#TYPE "Foundry Trap: MRP Cam Error"
	--#SUMMARY "%s."
	--#ARGUMENTS { 0 }
	--#SEVERITY WARNING
	--#STATE OPERATIONAL
   ::= 80

snTrapChasPwrSupplyOK TRAP-TYPE
   ENTERPRISE foundry
   VARIABLES { snChasPwrSupplyIndex, snChasPwrSupplyDescription }
   DESCRIPTION
       "The SNMP trap that is generated when a power supply operational
        status changed from failure to normal."
	--#TYPE "Foundry Trap: Power Supply OK"
	--#SUMMARY "Power supply %d (%s)  OK."
	--#ARGUMENTS { 0, 1 }
	--#SEVERITY MINOR
	--#STATE OPERATIONAL
   ::= 81


snTrapVrrpeIfStateChange TRAP-TYPE
   ENTERPRISE foundry
   VARIABLES { snAgGblTrapMessage }
   DESCRIPTION
       "The SNMP trap that is generated when a VRRPE routing device
       switched between states master, backup, intialized or uknown."
	--#TYPE "Foundry Trap: VRRPE Interface Change"
	--#SUMMARY "%s."
	--#ARGUMENTS { 0 }
	--#SEVERITY WARNING
	--#STATE OPERATIONAL
   ::= 82

snTrapVsrpIfStateChange TRAP-TYPE
   ENTERPRISE foundry
   VARIABLES { snAgGblTrapMessage }
   DESCRIPTION
       "The SNMP trap that is generated when a VSRP switching and routing device
       switched between states master, backup, intialized or uknown."
	--#TYPE "Foundry Trap: VSRP Interface Change"
	--#SUMMARY "%s."
	--#ARGUMENTS { 0 }
	--#SEVERITY WARNING
	--#STATE OPERATIONAL
   ::= 83

snTrapSrcIpAddressViolation TRAP-TYPE
   ENTERPRISE foundry
   VARIABLES { snAgGblTrapMessage }
   DESCRIPTION
       "The SNMP trap that is generated when a rogue device spoofs source
       IP address for denial of service attack."
	--#TYPE "Foundry Trap: Intruder Source IP Address"
	--#SUMMARY "%s."
	--#ARGUMENTS { 0 }
	--#SEVERITY WARNING
	--#STATE OPERATIONAL
   ::= 84

snTrapMacAuthEnable TRAP-TYPE
   ENTERPRISE foundry
   VARIABLES { snAgGblTrapMessage }
   DESCRIPTION
       "The SNMP trap that is generated when MAC-Authentication is enabled 
	    on an interface."
	--#TYPE "Foundry Trap: MAC-Authentication enabled"
	--#SUMMARY "%s."
	--#ARGUMENTS { 0 }
	--#SEVERITY INFORMATIONAL
	--#STATE OPERATIONAL
   ::= 85

snTrapMacAuthDisable TRAP-TYPE
   ENTERPRISE foundry
   VARIABLES { snAgGblTrapMessage }
   DESCRIPTION
       "The SNMP trap that is generated when MAC-Authentication is disabled 
	    on an interface."
	--#TYPE "Foundry Trap: MAC-Authentication disabled"
	--#SUMMARY "%s."
	--#ARGUMENTS { 0 }
	--#SEVERITY INFORMATIONAL
	--#STATE OPERATIONAL
   ::= 86

snTrapMacAuthMACAccepted TRAP-TYPE
   ENTERPRISE foundry
   VARIABLES { snAgGblTrapMessage }
   DESCRIPTION
       "The SNMP trap that is generated when MAC-Authentication is successful 
	    on an interface."
	--#TYPE "Foundry Trap: MAC-Authentication success"
	--#SUMMARY "%s."
	--#ARGUMENTS { 0 }
	--#SEVERITY INFORMATIONAL
	--#STATE OPERATIONAL
   ::= 87

snTrapMacAuthMACRejected TRAP-TYPE
   ENTERPRISE foundry
   VARIABLES { snAgGblTrapMessage }
   DESCRIPTION
       "The SNMP trap that is generated when MAC-Authentication is failed 
	    on an interface."
	--#TYPE "Foundry Trap: MAC-Authentication failure"
	--#SUMMARY "%s."
	--#ARGUMENTS { 0 }
	--#SEVERITY WARNING
	--#STATE OPERATIONAL
   ::= 88

snTrapMacAuthPortDisabled TRAP-TYPE
   ENTERPRISE foundry
   VARIABLES { snAgGblTrapMessage }
   DESCRIPTION
       "The SNMP trap that is generated when an interface is disabled due to
	    MAC-Authentication detecting a DOS attack on that interface."
	--#TYPE "Foundry Trap: MAC-Authentication port disabled"
	--#SUMMARY "%s."
	--#ARGUMENTS { 0 }
	--#SEVERITY CRITICAL
	--#STATE OPERATIONAL
   ::= 89

-- 90 through 103 are OSPFv3 traps

snTrapClientLoginReject TRAP-TYPE
   ENTERPRISE foundry
   VARIABLES { snAgGblTrapMessage }
   DESCRIPTION
       "The SNMP trap that is generated when a login attempt by a 
       telnet or SSH client fails."
	--#TYPE "Foundry Trap: Client Login Reject"
	--#SUMMARY "%s."
	--#ARGUMENTS { 0 }
	--#SEVERITY INFORMATIONAL
	--#STATE OPERATIONAL
   ::= 110

snTrapLocalUserConfigChange TRAP-TYPE
   ENTERPRISE foundry
   VARIABLES { snAgGblTrapMessage }
   DESCRIPTION
       "The SNMP trap that is generated when a local user configuration is changed."
	--#TYPE "Foundry Trap: Local User Config Change"
	--#SUMMARY "%s."
	--#ARGUMENTS { 0 }
	--#SEVERITY INFORMATIONAL
	--#STATE OPERATIONAL
   ::= 111

snTrapVlanConfigChange TRAP-TYPE
   ENTERPRISE foundry
   VARIABLES { snAgGblTrapMessage }
   DESCRIPTION
       "The SNMP trap that is generated when a vlan configuration is changed."
	--#TYPE "Foundry Trap: Vlan Config Change"
	--#SUMMARY "%s."
	--#ARGUMENTS { 0 }
	--#SEVERITY INFORMATIONAL
	--#STATE OPERATIONAL
   ::= 112

snTrapAclConfigChange TRAP-TYPE
   ENTERPRISE foundry
   VARIABLES { snAgGblTrapMessage }
   DESCRIPTION
       "The SNMP trap that is generated when a ACL configuration is changed."
	--#TYPE "Foundry Trap: ACL Config Change"
	--#SUMMARY "%s."
	--#ARGUMENTS { 0 }
	--#SEVERITY INFORMATIONAL
	--#STATE OPERATIONAL
   ::= 113

snTrapMacFilterConfigChange TRAP-TYPE
   ENTERPRISE foundry
   VARIABLES { snAgGblTrapMessage }
   DESCRIPTION
       "The SNMP trap that is generated when a MAC Filter configuration is changed."
	--#TYPE "Foundry Trap: MAC Filter Config Change"
	--#SUMMARY "%s."
	--#ARGUMENTS { 0 }
	--#SEVERITY INFORMATIONAL
	--#STATE OPERATIONAL
   ::= 114

snTrapSNMPConfigChange TRAP-TYPE
   ENTERPRISE foundry
   VARIABLES { snAgGblTrapMessage }
   DESCRIPTION
       "The SNMP trap that is generated when a SNMP configuration is changed."
	--#TYPE "Foundry Trap: SNMP Config Change"
	--#SUMMARY "%s."
	--#ARGUMENTS { 0 }
	--#SEVERITY INFORMATIONAL
	--#STATE OPERATIONAL
   ::= 115

snTrapSyslogConfigChange TRAP-TYPE
   ENTERPRISE foundry
   VARIABLES { snAgGblTrapMessage }
   DESCRIPTION
       "The SNMP trap that is generated when a Syslog configuration is changed."
	--#TYPE "Foundry Trap: Syslog Config Change"
	--#SUMMARY "%s."
	--#ARGUMENTS { 0 }
	--#SEVERITY INFORMATIONAL
	--#STATE OPERATIONAL
   ::= 116

snTrapPasswordConfigChange TRAP-TYPE
   ENTERPRISE foundry
   VARIABLES { snAgGblTrapMessage }
   DESCRIPTION
       "The SNMP trap that is generated when enable or line password is changed."
	--#TYPE "Foundry Trap: Password Config Change"
	--#SUMMARY "%s."
	--#ARGUMENTS { 0 }
	--#SEVERITY INFORMATIONAL
	--#STATE OPERATIONAL
   ::= 117

snTrapServerStatusChange TRAP-TYPE
   ENTERPRISE foundry
   VARIABLES { snAgGblTrapMessage }
   DESCRIPTION
       "The SNMP trap that is generated when a server is disabled or enabled."
	--#TYPE "Foundry Trap: Server Status Change"
	--#SUMMARY "%s."
	--#ARGUMENTS { 0 }
	--#SEVERITY INFORMATIONAL
	--#STATE OPERATIONAL
   ::= 118

snTrapL4RealServerPortMaxConnectionLimitReached TRAP-TYPE
   ENTERPRISE foundry
   VARIABLES { snAgGblTrapMessage }
   DESCRIPTION
       "The SNMP trap that is generated when the real server's port reaches
       maximum number of connections."
	--#TYPE "Foundry Trap: L4 Real Server Port Max Connection Limit"
	--#SUMMARY "%s"
	--#ARGUMENTS { 0 }
	--#SEVERITY WARNING
	--#STATE OPERATIONAL
   ::= 119

snTrapL4LinkDown TRAP-TYPE
   ENTERPRISE foundry
   VARIABLES { snL4TrapLinkName, snL4LinkVirtualInterface }
   DESCRIPTION
       "The SNMP trap that is generated when the ISP link goes down."
	--#TYPE "Foundry Trap: L4 "
	--#SUMMARY "ISP Link %s bound to ve %d is down."
	--#ARGUMENTS { 0, 1 }
	--#SEVERITY WARNING
	--#STATE OPERATIONAL
   ::= 120

snTrapL4LinkUp TRAP-TYPE
   ENTERPRISE foundry
   VARIABLES { snL4TrapLinkName, snL4LinkVirtualInterface }
   DESCRIPTION
       "The SNMP trap that is generated when the ISP link goes up."
	--#TYPE "Foundry Trap: L4 "
	--#SUMMARY "ISP Link %s bound to ve %d is up."
	--#ARGUMENTS { 0, 1 }
	--#SEVERITY WARNING
	--#STATE OPERATIONAL
   ::= 121

snTrapPortPriorityChange TRAP-TYPE
   ENTERPRISE foundry
   VARIABLES { snAgGblTrapMessage }
   DESCRIPTION
       "The SNMP trap that is generated when the priority of a port is changed."
	--#TYPE "Foundry Trap: Port Priority Change"
	--#SUMMARY "%s."
	--#ARGUMENTS { 0 }
	--#SEVERITY INFORMATIONAL
	--#STATE OPERATIONAL
   ::= 122

snTrapAutoPortDisableTrigger TRAP-TYPE
   ENTERPRISE foundry
   VARIABLES { snAgGblTrapMessage }
   DESCRIPTION
       "The SNMP trap that is generated when automatic port disable was triggered."
	--#TYPE "Foundry Trap: Automatic Port Disable Triggered "
	--#SUMMARY "%s."
	--#ARGUMENTS { 0 }
	--#SEVERITY ALERTS
	--#STATE OPERATIONAL
   ::= 123

snTrapAutoPortDisableRelease TRAP-TYPE
   ENTERPRISE foundry
   VARIABLES { snAgGblTrapMessage }
   DESCRIPTION
       "The SNMP trap that is generated when automatic port disable was released."
	--#TYPE "Foundry Trap: Automatic Port Disable Released "
	--#SUMMARY "%s."
	--#ARGUMENTS { 0 }
	--#SEVERITY ALERTS
	--#STATE OPERATIONAL
   ::= 124

snTrapPnPStatusChange TRAP-TYPE
   ENTERPRISE foundry
   VARIABLES { wgPnPStatus, wgPnPStatus, snAgGblTrapMessage }
   DESCRIPTION
       "The SNMP trap that is generated when plug-and-play status change."
	--#TYPE "Foundry Trap: Plug-and-play Status Change "
	--#SUMMARY "Old Pnp status: %d, new Pnp status: %d, msg: %s."
	--#ARGUMENTS { 0, 1, 2 }
	--#SEVERITY NOTIFICATIONS
	--#STATE OPERATIONAL
   ::= 125

snTrapWirelessIsrpPeerStateChange TRAP-TYPE
   ENTERPRISE foundry
   VARIABLES { snAgGblTrapMessage }
   DESCRIPTION
       "The SNMP trap that is generated when ISRP Peer changes state."
	--#TYPE "Foundry Trap: ISRP Peer's state has changed  "
	--#SUMMARY "%s."
	--#ARGUMENTS { 0 }
	--#SEVERITY NOTIFICATIONS
	--#STATE OPERATIONAL
   ::= 126

snTrapWirelessStationStateChange TRAP-TYPE
   ENTERPRISE foundry
   VARIABLES { snAgGblTrapMessage }
   DESCRIPTION
       "The SNMP trap that is generated when a wireless station's state changes."
	--#TYPE "Foundry Trap: Wireless Station's state has changed."
	--#SUMMARY "%s."
	--#ARGUMENTS { 0 }
	--#SEVERITY NOTIFICATIONS
	--#STATE OPERATIONAL
   ::= 127

snTrapWirelessStationRoamingEventTriggered TRAP-TYPE
   ENTERPRISE foundry
   VARIABLES { snAgGblTrapMessage }
   DESCRIPTION
       "The SNMP trap that is generated when we received a MOVE request from
   the AP"
	--#TYPE "Foundry Trap: Station has roamed "
	--#SUMMARY "%s."
	--#ARGUMENTS { 0 }
	--#SEVERITY NOTIFICATIONS
	--#STATE OPERATIONAL
   ::= 128

snTrapWirelessSappStateChange TRAP-TYPE
   ENTERPRISE foundry
   VARIABLES { snAgGblTrapMessage }
   DESCRIPTION
       "The SNMP trap that is generated when SAPP between an AP and a FIPS
   changes state."
	--#TYPE "Foundry Trap: SAPP between AP and FIPS changes state. "
	--#SUMMARY "%s."
	--#ARGUMENTS { 0 }
	--#SEVERITY NOTIFICATIONS
	--#STATE OPERATIONAL
   ::= 129

snTrapExternalPowerConnectionStatus TRAP-TYPE
   ENTERPRISE foundry
   VARIABLES { snAgGblTrapMessage }
   DESCRIPTION
       "The SNMP trap that is generated when the external power supply
       connecting or disconnecting to a power over ethernet module."
	--#TYPE "Foundry Trap: External Power Supply Change"
	--#SUMMARY "%s."
	--#ARGUMENTS { 0 }
	--#SEVERITY ALERTS
	--#STATE OPERATIONAL
   ::= 130

snTrapDot1xSecurityViolation TRAP-TYPE
   ENTERPRISE foundry
   VARIABLES { snAgGblTrapMessage }
   DESCRIPTION
       "The SNMP trap that is generated when a malicious mac
       address was detected."
	--#TYPE "Foundry Trap: 802.1x Security Violation"
	--#SUMMARY "%s."
	--#ARGUMENTS { 0 }
	--#SEVERITY ALERTS
	--#STATE OPERATIONAL
   ::= 131

snTrapDot1xPortLinkChange TRAP-TYPE
   ENTERPRISE foundry
   VARIABLES { snAgGblTrapMessage }
   DESCRIPTION
       "The SNMP trap that is generated when software port link status
       has changed to up or down."
	--#TYPE "Foundry Trap: 802.1x Port Link Change"
	--#SUMMARY "%s."
	--#ARGUMENTS { 0 }
	--#SEVERITY NOTIFICATIONS
	--#STATE OPERATIONAL
   ::= 132

snTrapDot1xPortControlChange TRAP-TYPE
   ENTERPRISE foundry
   VARIABLES { snAgGblTrapMessage }
   DESCRIPTION
       "The SNMP trap that is generated when software port control status
       has changed to authorize or unauthorize."
	--#TYPE "Foundry Trap: 802.1x Port Control Change"
	--#SUMMARY "%s."
	--#ARGUMENTS { 0 }
	--#SEVERITY NOTIFICATIONS
	--#STATE OPERATIONAL
   ::= 133

snTrapDot1xVlanIdChange TRAP-TYPE
   ENTERPRISE foundry
   VARIABLES { snAgGblTrapMessage }
   DESCRIPTION
       "The SNMP trap that is generated when VLAN ID of a port
       has changed."
	--#TYPE "Foundry Trap: 802.1x VLAN ID Change"
	--#SUMMARY "%s."
	--#ARGUMENTS { 0 }
	--#SEVERITY NOTIFICATIONS
	--#STATE OPERATIONAL
   ::= 134

snTrapDot1xFilterSetupFailure TRAP-TYPE
   ENTERPRISE foundry
   VARIABLES { snAgGblTrapMessage }
   DESCRIPTION
       "The SNMP trap that is generated when software failed
       to setup a filter to a mac address of a port."
	--#TYPE "Foundry Trap: 802.1x Filter Setup Failure"
	--#SUMMARY "%s."
	--#ARGUMENTS { 0 }
	--#SEVERITY NOTIFICATIONS
	--#STATE OPERATIONAL
   ::= 135

snTrapDot1xError TRAP-TYPE
   ENTERPRISE foundry
   VARIABLES { snAgGblTrapMessage }
   DESCRIPTION
       "The SNMP trap that is generated when software detected
       system error."
	--#TYPE "Foundry Trap: 802.1x Error"
	--#SUMMARY "%s."
	--#ARGUMENTS { 0 }
	--#SEVERITY DEBUGGING
	--#STATE OPERATIONAL
   ::= 136

snTrapPortConfigChange TRAP-TYPE
   ENTERPRISE foundry
   VARIABLES { snAgGblTrapMessage }
   DESCRIPTION
       "The SNMP trap that is generated when a port configuration is changed."
	--#TYPE "Foundry Trap: Port Config Change"
	--#SUMMARY "%s."
	--#ARGUMENTS { 0 }
	--#SEVERITY INFORMATIONAL
	--#STATE OPERATIONAL
   ::= 137

snTrapMacAuthVlanIdChange TRAP-TYPE
   ENTERPRISE foundry
   VARIABLES { snAgGblTrapMessage }
   DESCRIPTION
       "The SNMP trap that is generated when VLAN ID of a port
       has changed."
	--#TYPE "Foundry Trap: MAC-Authentication VLAN ID Change"
	--#SUMMARY "%s."
	--#ARGUMENTS { 0 }
	--#SEVERITY NOTIFICATIONS
	--#STATE OPERATIONAL
   ::= 138

snTrapWebAuthEnabled TRAP-TYPE
   ENTERPRISE foundry
   VARIABLES { snAgGblTrapMessage }
   DESCRIPTION
       "The SNMP trap that is generated when web authentication is enabled."
	--#TYPE "Foundry Trap: Web Authentication Enabled"
	--#SUMMARY "%s."
	--#ARGUMENTS { 0 }
	--#SEVERITY INFORMATIONAL
	--#STATE OPERATIONAL
   ::= 139

snTrapWebAuthDisabled TRAP-TYPE
   ENTERPRISE foundry
   VARIABLES { snAgGblTrapMessage }
   DESCRIPTION
       "The SNMP trap that is generated when web authentication is disabled."
	--#TYPE "Foundry Trap: Web Authentication Disabled"
	--#SUMMARY "%s."
	--#ARGUMENTS { 0 }
	--#SEVERITY INFORMATIONAL
	--#STATE OPERATIONAL
   ::= 140

snTrapIpConfigChange TRAP-TYPE
   ENTERPRISE foundry
   VARIABLES { snAgGblTrapMessage }
   DESCRIPTION
       "The SNMP trap that is generated when IP system address changes."
	--#TYPE "Foundry Trap: IP Configuration Change"
	--#SUMMARY "%s."
	--#ARGUMENTS { 0 }
	--#SEVERITY INFORMATIONAL
	--#STATE OPERATIONAL
   ::= 141

snTrapIpv6ConfigChange TRAP-TYPE
   ENTERPRISE foundry
   VARIABLES { snAgGblTrapMessage }
   DESCRIPTION
       "The SNMP trap that is generated when IPv6 system address changes."
	--#TYPE "Foundry Trap: IPv6 Configuration Change"
	--#SUMMARY "%s."
	--#ARGUMENTS { 0 }
	--#SEVERITY INFORMATIONAL
	--#STATE OPERATIONAL
   ::= 142

snTrapMacAuthRadiusTimeout TRAP-TYPE
   ENTERPRISE foundry
   VARIABLES { snAgGblTrapMessage }
   DESCRIPTION
       "The SNMP trap that is generated when a request from Mac-Auth
       to RADIUS has not been answered within the retry and time limit."
	--#TYPE "Foundry Trap: MAC-Authentication RADIUS timeout"
	--#SUMMARY "%s."
	--#ARGUMENTS { 0 }
	--#SEVERITY NOTIFICATIONS
	--#STATE OPERATIONAL
   ::= 143

snTrapDot1xRadiusTimeout TRAP-TYPE
   ENTERPRISE foundry
   VARIABLES { snAgGblTrapMessage }
   DESCRIPTION
       "The SNMP trap that is generated when a request from 802.1x
       to RADIUS has not been answered within the retry and time limit."
	--#TYPE "Foundry Trap: MAC-Authentication RADIUS timeout"
	--#SUMMARY "%s."
	--#ARGUMENTS { 0 }
	--#SEVERITY NOTIFICATIONS
	--#STATE OPERATIONAL
   ::= 144

snTrapUDLDLinkDown TRAP-TYPE
   ENTERPRISE foundry
   VARIABLES { ifIndex, snAgGblTrapMessage }
   DESCRIPTION
       "The SNMP trap that is generated when UDLD port link status
       has changed to down."
	--#TYPE "Foundry Trap: UDLD Port Link Down"
	--#SUMMARY "%s."
	--#ARGUMENTS { 1 }
	--#SEVERITY NOTIFICATIONS
	--#STATE OPERATIONAL
   ::= 145

snTrapUDLDLinkUp TRAP-TYPE
   ENTERPRISE foundry
   VARIABLES { ifIndex, snAgGblTrapMessage }
   DESCRIPTION
       "The SNMP trap that is generated when UDLD port link status
       has changed to up."
	--#TYPE "Foundry Trap: UDLD Port Link Up"
	--#SUMMARY "%s."
	--#ARGUMENTS { 1 }
	--#SEVERITY NOTIFICATIONS
	--#STATE OPERATIONAL
   ::= 146

snTrapMacBasedVlanEnabled TRAP-TYPE
   ENTERPRISE foundry
   VARIABLES { snAgGblTrapMessage }
   DESCRIPTION
       "The SNMP trap that is generated when MAC based VLAN is enabled."
 	--#TYPE "Foundry Trap: MAC based VLAN enabled"
	--#SUMMARY "%s."
	--#ARGUMENTS { 0 }
	--#SEVERITY NOTIFICATIONS
	--#STATE OPERATIONAL
   ::= 147

snTrapMacBasedVlanDisabled TRAP-TYPE
   ENTERPRISE foundry
   VARIABLES { snAgGblTrapMessage }
   DESCRIPTION
       "The SNMP trap that is generated when MAC based VLAN is disabled."
 	--#TYPE "Foundry Trap: MAC based VLAN disabled"
	--#SUMMARY "%s."
	--#ARGUMENTS { 0 }
	--#SEVERITY NOTIFICATIONS
	--#STATE OPERATIONAL
   ::= 148

snTrapChasFanNormal TRAP-TYPE
   ENTERPRISE foundry
   VARIABLES { snChasFanIndex, snChasFanDescription }
   DESCRIPTION
       "The SNMP trap that is generated when a fan operational status
        changed from failure to normal."
	--#TYPE "Foundry Trap: Fan OK"
	--#SUMMARY "Fan  %d (%s)  OK."
	--#ARGUMENTS { 0, 1 }
	--#SEVERITY MINOR
	--#STATE OPERATIONAL
   ::=  149

snTrapStpRootGuardDetect TRAP-TYPE
   ENTERPRISE foundry
   VARIABLES {ifIndex, snVLanByPortCfgVLanId, snAgGblTrapMessage}
   DESCRIPTION
	   "The SNMP trap that is generated when VLAN's Root-Guarded port received superior BPDU."
	--#TYPE "Foundry Trap:  Stp root guard detect"
	--#SUMMARY "%s."
	--#ARGUMENTS { 2 }
	--#SEVERITY NOTIFICATIONS
	--#STATE OPERATIONAL
   ::= 150

snTrapStpRootGuardExpire TRAP-TYPE
   ENTERPRISE foundry
   VARIABLES {ifIndex, snVLanByPortCfgVLanId, snAgGblTrapMessage}
   DESCRIPTION
	       "The SNMP trap that is generated when VLAN's ports's Root-Guard expire."
	--#TYPE "Foundry Trap:  Stp root guard expire"
	--#SUMMARY "%s."
	--#ARGUMENTS { 2 }
	--#SEVERITY NOTIFICATIONS
	--#STATE OPERATIONAL
   ::= 151
 
snTrapStpBPDUGuardDetect TRAP-TYPE
   ENTERPRISE foundry
   VARIABLES {ifIndex, snVLanByPortCfgVLanId, snAgGblTrapMessage}
   DESCRIPTION
       "The SNMP trap that is generated when VLAN's BPDU-guarded port received BPDU . "
	--#TYPE "Foundry Trap: STP BPDU guard "
	--#SUMMARY "%s."
	--#ARGUMENTS { 2 }
	--#SEVERITY NOTIFICATIONS
	--#STATE OPERATIONAL
   ::= 152

snTrapMstpBPDUGuardDetect TRAP-TYPE
   ENTERPRISE foundry
   VARIABLES {ifIndex, snAgGblTrapMessage}
   DESCRIPTION
       "The SNMP trap that is generated when BPDU-guarded port received BPDU . "
	--#TYPE "Foundry Trap: MSTP BPDU guard "
	--#SUMMARY "%s."
	--#ARGUMENTS { 1 }
	--#SEVERITY NOTIFICATIONS
	--#STATE OPERATIONAL
   ::= 153

snTrapErrorDisableAction TRAP-TYPE
   ENTERPRISE foundry
   VARIABLES {ifIndex, snAgGblTrapMessage}
   DESCRIPTION
       "The SNMP trap that is generated when  Interface error-disable is hit or recovery times out . "
	--#TYPE "Foundry Trap:  Error-disable hit or recovery times out"
	--#SUMMARY "%s."
	--#ARGUMENTS { 1 }
	--#SEVERITY NOTIFICATIONS
	--#STATE OPERATIONAL
   ::= 154

snTrapLACPLinkStateChange TRAP-TYPE
   ENTERPRISE foundry
   VARIABLES {ifIndex, snAgGblTrapMessage}
   DESCRIPTION
       "The SNMP trap that is generated when LACP port changes its state. "
	 --#TYPE "Foundry Trap:  LACP port state change"
	 --#SUMMARY "%s."
	 --#ARGUMENTS {  1  }
	 --#SEVERITY NOTIFICATIONS
	 --#STATE OPERATIONAL
   ::= 155

END
